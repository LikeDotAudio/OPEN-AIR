OPENAIR-MIB DEFINITIONS ::= BEGIN

IMPORTS
    MODULE-IDENTITY, OBJECT-TYPE, enterprises FROM SNMPv2-SMI
    DisplayString FROM SNMPv2-TC;

openAirMIB MODULE-IDENTITY
    LAST-UPDATED "202603231610Z"
    ORGANIZATION "OPEN-AIR Project"
    CONTACT-INFO "Anthony Peter Kuzub"
    DESCRIPTION "MQTT-Aligned OID Tree for OPEN-AIR."
    REVISION "202603231610Z"
    DESCRIPTION "Strictly unique path-aligned generation."
    ::= { enterprises 65300 }

v1 OBJECT IDENTIFIER ::= { openAirMIB 1 }

-- MQTT: OPEN-AIR/status
status7b00 OBJECT-TYPE
    SYNTAX      DisplayString
    MAX-ACCESS  read-write
    STATUS      current
    DESCRIPTION "Source: OPEN-AIR/status"
    ::= { v1 25884 }

assets79d1 OBJECT IDENTIFIER ::= { v1 32142 }
spectrum9965 OBJECT IDENTIFIER ::= { assets79d1 0 }
instrument5d2b OBJECT IDENTIFIER ::= { spectrum9965 3 }
frequencyf29b OBJECT IDENTIFIER ::= { instrument5d2b 1 }
spectrumInstrumentfrequency1a26 OBJECT IDENTIFIER ::= { frequencyf29b 33369 }
blocks4fa6 OBJECT IDENTIFIER ::= { spectrumInstrumentfrequency1a26 54840 }
frequency5ff2 OBJECT IDENTIFIER ::= { blocks4fa6 36210 }
-- MQTT: OPEN-AIR/Assets/Spectrum/Instrument/frequency/Spectrum_Instrument_frequency/blocks/Frequency/center_freq_MHz
centerfreqMHzf074 OBJECT-TYPE
    SYNTAX      DisplayString
    MAX-ACCESS  read-write
    STATUS      current
    DESCRIPTION "Source: OPEN-AIR/Assets/Spectrum/Instrument/frequency/Spectrum_Instrument_frequency/blocks/Frequency/center_freq_MHz"
    ::= { frequency5ff2 31728 }

-- MQTT: OPEN-AIR/Assets/Spectrum/Instrument/frequency/Spectrum_Instrument_frequency/blocks/Frequency/span_freq_MHz
spanfreqMHza7ab OBJECT-TYPE
    SYNTAX      DisplayString
    MAX-ACCESS  read-write
    STATUS      current
    DESCRIPTION "Source: OPEN-AIR/Assets/Spectrum/Instrument/frequency/Spectrum_Instrument_frequency/blocks/Frequency/span_freq_MHz"
    ::= { frequency5ff2 48513 }

quickSpan5766 OBJECT IDENTIFIER ::= { blocks4fa6 36959 }
-- MQTT: OPEN-AIR/Assets/Spectrum/Instrument/frequency/Spectrum_Instrument_frequency/blocks/Quick Span/Span
spanc087 OBJECT-TYPE
    SYNTAX      DisplayString
    MAX-ACCESS  read-write
    STATUS      current
    DESCRIPTION "Source: OPEN-AIR/Assets/Spectrum/Instrument/frequency/Spectrum_Instrument_frequency/blocks/Quick Span/Span"
    ::= { quickSpan5766 64492 }

startStopc7a1 OBJECT IDENTIFIER ::= { blocks4fa6 53393 }
-- MQTT: OPEN-AIR/Assets/Spectrum/Instrument/frequency/Spectrum_Instrument_frequency/blocks/Start Stop/start_freq_MHz
startfreqMHz6298 OBJECT-TYPE
    SYNTAX      DisplayString
    MAX-ACCESS  read-write
    STATUS      current
    DESCRIPTION "Source: OPEN-AIR/Assets/Spectrum/Instrument/frequency/Spectrum_Instrument_frequency/blocks/Start Stop/start_freq_MHz"
    ::= { startStopc7a1 2369 }

-- MQTT: OPEN-AIR/Assets/Spectrum/Instrument/frequency/Spectrum_Instrument_frequency/blocks/Start Stop/stop_freq_MHz
stopfreqMHz7735 OBJECT-TYPE
    SYNTAX      DisplayString
    MAX-ACCESS  read-write
    STATUS      current
    DESCRIPTION "Source: OPEN-AIR/Assets/Spectrum/Instrument/frequency/Spectrum_Instrument_frequency/blocks/Start Stop/stop_freq_MHz"
    ::= { startStopc7a1 38481 }

bandwidth5eed OBJECT IDENTIFIER ::= { instrument5d2b 2 }
spectrumInstrumentbandwidth88b1 OBJECT IDENTIFIER ::= { bandwidth5eed 5104 }
blocks3908 OBJECT IDENTIFIER ::= { spectrumInstrumentbandwidth88b1 16720 }
resolutionBandwidth9ba3 OBJECT IDENTIFIER ::= { blocks3908 1893 }
-- MQTT: OPEN-AIR/Assets/Spectrum/Instrument/bandwidth/Spectrum_Instrument_bandwidth/blocks/Resolution Bandwidth/Resolution Band Width
resolutionBandWidth892b OBJECT-TYPE
    SYNTAX      DisplayString
    MAX-ACCESS  read-write
    STATUS      current
    DESCRIPTION "Source: OPEN-AIR/Assets/Spectrum/Instrument/bandwidth/Spectrum_Instrument_bandwidth/blocks/Resolution Bandwidth/Resolution Band Width"
    ::= { resolutionBandwidth9ba3 17396 }

rBWfc8a OBJECT IDENTIFIER ::= { resolutionBandwidth9ba3 34210 }
-- MQTT: OPEN-AIR/Assets/Spectrum/Instrument/bandwidth/Spectrum_Instrument_bandwidth/blocks/Resolution Bandwidth/RBW/dial_config
dialconfigb398 OBJECT-TYPE
    SYNTAX      DisplayString
    MAX-ACCESS  read-write
    STATUS      current
    DESCRIPTION "Source: OPEN-AIR/Assets/Spectrum/Instrument/bandwidth/Spectrum_Instrument_bandwidth/blocks/Resolution Bandwidth/RBW/dial_config"
    ::= { rBWfc8a 25960 }

-- MQTT: OPEN-AIR/Assets/Spectrum/Instrument/bandwidth/Spectrum_Instrument_bandwidth/blocks/Resolution Bandwidth/RBW/fader_config
faderconfig4905 OBJECT-TYPE
    SYNTAX      DisplayString
    MAX-ACCESS  read-write
    STATUS      current
    DESCRIPTION "Source: OPEN-AIR/Assets/Spectrum/Instrument/bandwidth/Spectrum_Instrument_bandwidth/blocks/Resolution Bandwidth/RBW/fader_config"
    ::= { rBWfc8a 31626 }

sweepTime1a75 OBJECT IDENTIFIER ::= { blocks3908 43407 }
sweeptimesettingcee7 OBJECT IDENTIFIER ::= { sweepTime1a75 22849 }
-- MQTT: OPEN-AIR/Assets/Spectrum/Instrument/bandwidth/Spectrum_Instrument_bandwidth/blocks/Sweep Time/sweep_time_setting/dial_config
dialconfigad08 OBJECT-TYPE
    SYNTAX      DisplayString
    MAX-ACCESS  read-write
    STATUS      current
    DESCRIPTION "Source: OPEN-AIR/Assets/Spectrum/Instrument/bandwidth/Spectrum_Instrument_bandwidth/blocks/Sweep Time/sweep_time_setting/dial_config"
    ::= { sweeptimesettingcee7 43416 }

videoBandwidthe565 OBJECT IDENTIFIER ::= { blocks3908 45850 }
vbwMHz4e7c OBJECT IDENTIFIER ::= { videoBandwidthe565 18590 }
-- MQTT: OPEN-AIR/Assets/Spectrum/Instrument/bandwidth/Spectrum_Instrument_bandwidth/blocks/Video Bandwidth/vbw_MHz/fader_config
faderconfigf1b8 OBJECT-TYPE
    SYNTAX      DisplayString
    MAX-ACCESS  read-write
    STATUS      current
    DESCRIPTION "Source: OPEN-AIR/Assets/Spectrum/Instrument/bandwidth/Spectrum_Instrument_bandwidth/blocks/Video Bandwidth/vbw_MHz/fader_config"
    ::= { vbwMHz4e7c 139 }

-- MQTT: OPEN-AIR/Assets/Spectrum/Instrument/bandwidth/Spectrum_Instrument_bandwidth/blocks/Video Bandwidth/vbw_MHz/dial_config
dialconfigb346 OBJECT-TYPE
    SYNTAX      DisplayString
    MAX-ACCESS  read-write
    STATUS      current
    DESCRIPTION "Source: OPEN-AIR/Assets/Spectrum/Instrument/bandwidth/Spectrum_Instrument_bandwidth/blocks/Video Bandwidth/vbw_MHz/dial_config"
    ::= { vbwMHz4e7c 27487 }

amplitudebf49 OBJECT IDENTIFIER ::= { instrument5d2b 3 }
spectrumInstrumentamplitude398c OBJECT IDENTIFIER ::= { amplitudebf49 38833 }
blocksa4e2 OBJECT IDENTIFIER ::= { spectrumInstrumentamplitude398c 10887 }
referenceLevel6721 OBJECT IDENTIFIER ::= { blocksa4e2 45561 }
refleveldBm86bf OBJECT IDENTIFIER ::= { referenceLevel6721 5605 }
-- MQTT: OPEN-AIR/Assets/Spectrum/Instrument/amplitude/Spectrum_Instrument_amplitude/blocks/Reference Level/ref_level_dBm/fader_config
faderconfig5d72 OBJECT-TYPE
    SYNTAX      DisplayString
    MAX-ACCESS  read-write
    STATUS      current
    DESCRIPTION "Source: OPEN-AIR/Assets/Spectrum/Instrument/amplitude/Spectrum_Instrument_amplitude/blocks/Reference Level/ref_level_dBm/fader_config"
    ::= { refleveldBm86bf 40042 }

-- MQTT: OPEN-AIR/Assets/Spectrum/Instrument/amplitude/Spectrum_Instrument_amplitude/blocks/Reference Level/ref_level_dBm/dial_config
dialconfigc523 OBJECT-TYPE
    SYNTAX      DisplayString
    MAX-ACCESS  read-write
    STATUS      current
    DESCRIPTION "Source: OPEN-AIR/Assets/Spectrum/Instrument/amplitude/Spectrum_Instrument_amplitude/blocks/Reference Level/ref_level_dBm/dial_config"
    ::= { refleveldBm86bf 51828 }

tracesf27c OBJECT IDENTIFIER ::= { instrument5d2b 5 }
spectrumInstrumenttraces8aee OBJECT IDENTIFIER ::= { tracesf27c 21678 }
blocks4e3d OBJECT IDENTIFIER ::= { spectrumInstrumenttraces8aee 28643 }
averagingdb61 OBJECT IDENTIFIER ::= { blocks4e3d 37350 }
-- MQTT: OPEN-AIR/Assets/Spectrum/Instrument/traces/Spectrum_Instrument_traces/blocks/Averaging/AVERAGING
aVERAGINGdc05 OBJECT-TYPE
    SYNTAX      DisplayString
    MAX-ACCESS  read-write
    STATUS      current
    DESCRIPTION "Source: OPEN-AIR/Assets/Spectrum/Instrument/traces/Spectrum_Instrument_traces/blocks/Averaging/AVERAGING"
    ::= { averagingdb61 64952 }

continuousea2a OBJECT IDENTIFIER ::= { blocks4e3d 63091 }
-- MQTT: OPEN-AIR/Assets/Spectrum/Instrument/traces/Spectrum_Instrument_traces/blocks/Continuous/CONTINUOUS_MODE
cONTINUOUSMODE5044 OBJECT-TYPE
    SYNTAX      DisplayString
    MAX-ACCESS  read-write
    STATUS      current
    DESCRIPTION "Source: OPEN-AIR/Assets/Spectrum/Instrument/traces/Spectrum_Instrument_traces/blocks/Continuous/CONTINUOUS_MODE"
    ::= { continuousea2a 1453 }

scan8571 OBJECT IDENTIFIER ::= { assets79d1 1 }
scan39a8 OBJECT IDENTIFIER ::= { scan8571 27445 }
blocks8eaa OBJECT IDENTIFIER ::= { scan39a8 46272 }
multidatasetgraphc492 OBJECT IDENTIFIER ::= { blocks8eaa 19071 }
oaDataRunningFilesfdbd OBJECT IDENTIFIER ::= { multidatasetgraphc492 9507 }
-- MQTT: OPEN-AIR/Assets/scan/scan/blocks/multi_dataset_graph/oaDataRunningFiles/MARKERS
mARKERS651d OBJECT-TYPE
    SYNTAX      DisplayString
    MAX-ACCESS  read-write
    STATUS      current
    DESCRIPTION "Source: OPEN-AIR/Assets/scan/scan/blocks/multi_dataset_graph/oaDataRunningFiles/MARKERS"
    ::= { oaDataRunningFilesfdbd 18452 }

-- MQTT: OPEN-AIR/Assets/scan/scan/blocks/multi_dataset_graph/oaDataRunningFiles/ref_linear
reflinear8ee1 OBJECT-TYPE
    SYNTAX      DisplayString
    MAX-ACCESS  read-write
    STATUS      current
    DESCRIPTION "Source: OPEN-AIR/Assets/scan/scan/blocks/multi_dataset_graph/oaDataRunningFiles/ref_linear"
    ::= { oaDataRunningFilesfdbd 30162 }

settings5e4f OBJECT IDENTIFIER ::= { multidatasetgraphc492 53222 }
-- MQTT: OPEN-AIR/Assets/scan/scan/blocks/multi_dataset_graph/settings/x_label
xlabela969 OBJECT-TYPE
    SYNTAX      DisplayString
    MAX-ACCESS  read-write
    STATUS      current
    DESCRIPTION "Source: OPEN-AIR/Assets/scan/scan/blocks/multi_dataset_graph/settings/x_label"
    ::= { settings5e4f 9887 }

-- MQTT: OPEN-AIR/Assets/scan/scan/blocks/multi_dataset_graph/settings/ylim
ylim8331 OBJECT-TYPE
    SYNTAX      DisplayString
    MAX-ACCESS  read-write
    STATUS      current
    DESCRIPTION "Source: OPEN-AIR/Assets/scan/scan/blocks/multi_dataset_graph/settings/ylim"
    ::= { settings5e4f 10649 }

-- MQTT: OPEN-AIR/Assets/scan/scan/blocks/multi_dataset_graph/settings/y_label
ylabelf1e2 OBJECT-TYPE
    SYNTAX      DisplayString
    MAX-ACCESS  read-write
    STATUS      current
    DESCRIPTION "Source: OPEN-AIR/Assets/scan/scan/blocks/multi_dataset_graph/settings/y_label"
    ::= { settings5e4f 11563 }

-- MQTT: OPEN-AIR/Assets/scan/scan/blocks/multi_dataset_graph/settings/xlim
xlim3b8d OBJECT-TYPE
    SYNTAX      DisplayString
    MAX-ACCESS  read-write
    STATUS      current
    DESCRIPTION "Source: OPEN-AIR/Assets/scan/scan/blocks/multi_dataset_graph/settings/xlim"
    ::= { settings5e4f 20220 }

-- MQTT: OPEN-AIR/Assets/scan/scan/blocks/multi_dataset_graph/settings/title
titlea421 OBJECT-TYPE
    SYNTAX      DisplayString
    MAX-ACCESS  read-write
    STATUS      current
    DESCRIPTION "Source: OPEN-AIR/Assets/scan/scan/blocks/multi_dataset_graph/settings/title"
    ::= { settings5e4f 21874 }

-- MQTT: OPEN-AIR/Assets/scan/scan/blocks/multi_dataset_graph/settings/show_grid
showgrid97d7 OBJECT-TYPE
    SYNTAX      DisplayString
    MAX-ACCESS  read-write
    STATUS      current
    DESCRIPTION "Source: OPEN-AIR/Assets/scan/scan/blocks/multi_dataset_graph/settings/show_grid"
    ::= { settings5e4f 55413 }

monitorse005 OBJECT IDENTIFIER ::= { assets79d1 2 }
graphs5c0a OBJECT IDENTIFIER ::= { monitorse005 00 }
monitors7920 OBJECT IDENTIFIER ::= { graphs5c0a 33517 }
settings2d1a OBJECT IDENTIFIER ::= { monitors7920 43006 }
-- MQTT: OPEN-AIR/Assets/monitors/Graphs/monitors/settings/show_grid
showgrid9a6a OBJECT-TYPE
    SYNTAX      DisplayString
    MAX-ACCESS  read-write
    STATUS      current
    DESCRIPTION "Source: OPEN-AIR/Assets/monitors/Graphs/monitors/settings/show_grid"
    ::= { settings2d1a 8149 }

-- MQTT: OPEN-AIR/Assets/monitors/Graphs/monitors/settings/y_label
ylabelc296 OBJECT-TYPE
    SYNTAX      DisplayString
    MAX-ACCESS  read-write
    STATUS      current
    DESCRIPTION "Source: OPEN-AIR/Assets/monitors/Graphs/monitors/settings/y_label"
    ::= { settings2d1a 20686 }

-- MQTT: OPEN-AIR/Assets/monitors/Graphs/monitors/settings/x_label
xlabel64e1 OBJECT-TYPE
    SYNTAX      DisplayString
    MAX-ACCESS  read-write
    STATUS      current
    DESCRIPTION "Source: OPEN-AIR/Assets/monitors/Graphs/monitors/settings/x_label"
    ::= { settings2d1a 23418 }

-- MQTT: OPEN-AIR/Assets/monitors/Graphs/monitors/settings/title
titledadf OBJECT-TYPE
    SYNTAX      DisplayString
    MAX-ACCESS  read-write
    STATUS      current
    DESCRIPTION "Source: OPEN-AIR/Assets/monitors/Graphs/monitors/settings/title"
    ::= { settings2d1a 43083 }

-- MQTT: OPEN-AIR/Assets/monitors/Graphs/monitors/settings/ylim
ylimccb0 OBJECT-TYPE
    SYNTAX      DisplayString
    MAX-ACCESS  read-write
    STATUS      current
    DESCRIPTION "Source: OPEN-AIR/Assets/monitors/Graphs/monitors/settings/ylim"
    ::= { settings2d1a 44436 }

-- MQTT: OPEN-AIR/Assets/monitors/Graphs/monitors/settings/xlim
xlim740c OBJECT-TYPE
    SYNTAX      DisplayString
    MAX-ACCESS  read-write
    STATUS      current
    DESCRIPTION "Source: OPEN-AIR/Assets/monitors/Graphs/monitors/settings/xlim"
    ::= { settings2d1a 51953 }

oaDataRunningFilesf000 OBJECT IDENTIFIER ::= { monitors7920 57987 }
-- MQTT: OPEN-AIR/Assets/monitors/Graphs/monitors/oaDataRunningFiles/MARKERS
mARKERS982e OBJECT-TYPE
    SYNTAX      DisplayString
    MAX-ACCESS  read-write
    STATUS      current
    DESCRIPTION "Source: OPEN-AIR/Assets/monitors/Graphs/monitors/oaDataRunningFiles/MARKERS"
    ::= { oaDataRunningFilesf000 51847 }

righttopd258 OBJECT IDENTIFIER ::= { assets79d1 65245 }
blocksba04 OBJECT IDENTIFIER ::= { righttopd258 19748 }
controlButtons30e5 OBJECT IDENTIFIER ::= { blocksba04 19809 }
-- MQTT: OPEN-AIR/Assets/right_top/blocks/Control_Buttons/Pause
pausef081 OBJECT-TYPE
    SYNTAX      DisplayString
    MAX-ACCESS  read-write
    STATUS      current
    DESCRIPTION "Source: OPEN-AIR/Assets/right_top/blocks/Control_Buttons/Pause"
    ::= { controlButtons30e5 26413 }

END
