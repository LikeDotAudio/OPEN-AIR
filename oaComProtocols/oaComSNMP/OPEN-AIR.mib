OPENAIR-MIB DEFINITIONS ::= BEGIN

IMPORTS
    MODULE-IDENTITY, OBJECT-TYPE, enterprises FROM SNMPv2-SMI
    DisplayString FROM SNMPv2-TC;

openAirMIB MODULE-IDENTITY
    LAST-UPDATED "202604030158Z"
    ORGANIZATION "OPEN-AIR Project"
    CONTACT-INFO "Anthony Peter Kuzub"
    DESCRIPTION "MQTT-Aligned OID Tree for OPEN-AIR."
    REVISION "202604030158Z"
    DESCRIPTION "Strictly unique path-aligned generation."
    ::= { enterprises 65300 }

v1 OBJECT IDENTIFIER ::= { openAirMIB 1 }

oSC6c63 OBJECT IDENTIFIER ::= { v1 20440 }
oSCAssetsa5ca OBJECT IDENTIFIER ::= { oSC6c63 64155 }
oSCAssetsSpectrum26e9 OBJECT IDENTIFIER ::= { oSCAssetsa5ca 938 }
oSCAssetsSpectrumInstrumentf0bf OBJECT IDENTIFIER ::= { oSCAssetsSpectrum26e9 52984 }
oSCAssetsSpectrumInstrumentBandwidth29ea OBJECT IDENTIFIER ::= { oSCAssetsSpectrumInstrumentf0bf 7055 }
oSCAssetsSpectrumInstrumentBandwidthSpectrumInstrumentbandwi537f OBJECT IDENTIFIER ::= { oSCAssetsSpectrumInstrumentBandwidth29ea 40162 }
oSCAssetsSpectrumInstrumentBandwidthSpectrumInstrumentbandwi8717 OBJECT IDENTIFIER ::= { oSCAssetsSpectrumInstrumentBandwidthSpectrumInstrumentbandwi537f 5252 }
oSCAssetsSpectrumInstrumentBandwidthSpectrumInstrumentbandwi6e26 OBJECT IDENTIFIER ::= { oSCAssetsSpectrumInstrumentBandwidthSpectrumInstrumentbandwi8717 42920 }
oSCAssetsSpectrumInstrumentBandwidthSpectrumInstrumentbandwi2af6 OBJECT IDENTIFIER ::= { oSCAssetsSpectrumInstrumentBandwidthSpectrumInstrumentbandwi6e26 33924 }
-- MQTT: OPEN-AIR/OSC/Assets/Spectrum/Instrument/bandwidth/Spectrum_Instrument_bandwidth/blocks/Resolution Bandwidth/RBW/dial_config
oSCAssetsSpectrumInstrumentBandwidthSpectrumInstrumentbandwie729 OBJECT-TYPE
    SYNTAX      DisplayString
    MAX-ACCESS  read-write
    STATUS      current
    DESCRIPTION "Source: OPEN-AIR/OSC/Assets/Spectrum/Instrument/bandwidth/Spectrum_Instrument_bandwidth/blocks/Resolution Bandwidth/RBW/dial_config"
    ::= { oSCAssetsSpectrumInstrumentBandwidthSpectrumInstrumentbandwi2af6 39189 }

-- MQTT: OPEN-AIR/OSC/Assets/Spectrum/Instrument/bandwidth/Spectrum_Instrument_bandwidth/blocks/Resolution Bandwidth/RBW/fader_config
oSCAssetsSpectrumInstrumentBandwidthSpectrumInstrumentbandwi670c OBJECT-TYPE
    SYNTAX      DisplayString
    MAX-ACCESS  read-write
    STATUS      current
    DESCRIPTION "Source: OPEN-AIR/OSC/Assets/Spectrum/Instrument/bandwidth/Spectrum_Instrument_bandwidth/blocks/Resolution Bandwidth/RBW/fader_config"
    ::= { oSCAssetsSpectrumInstrumentBandwidthSpectrumInstrumentbandwi2af6 40183 }

oSCAssetsSpectrumInstrumentBandwidthSpectrumInstrumentbandwi753d OBJECT IDENTIFIER ::= { oSCAssetsSpectrumInstrumentBandwidthSpectrumInstrumentbandwi8717 52390 }
oSCAssetsSpectrumInstrumentBandwidthSpectrumInstrumentbandwie4de OBJECT IDENTIFIER ::= { oSCAssetsSpectrumInstrumentBandwidthSpectrumInstrumentbandwi753d 34366 }
-- MQTT: OPEN-AIR/OSC/Assets/Spectrum/Instrument/bandwidth/Spectrum_Instrument_bandwidth/blocks/Video Bandwidth/vbw_MHz/dial_config
oSCAssetsSpectrumInstrumentBandwidthSpectrumInstrumentbandwie448 OBJECT-TYPE
    SYNTAX      DisplayString
    MAX-ACCESS  read-write
    STATUS      current
    DESCRIPTION "Source: OPEN-AIR/OSC/Assets/Spectrum/Instrument/bandwidth/Spectrum_Instrument_bandwidth/blocks/Video Bandwidth/vbw_MHz/dial_config"
    ::= { oSCAssetsSpectrumInstrumentBandwidthSpectrumInstrumentbandwie4de 2735 }

-- MQTT: OPEN-AIR/OSC/Assets/Spectrum/Instrument/bandwidth/Spectrum_Instrument_bandwidth/blocks/Video Bandwidth/vbw_MHz/fader_config
oSCAssetsSpectrumInstrumentBandwidthSpectrumInstrumentbandwi4c52 OBJECT-TYPE
    SYNTAX      DisplayString
    MAX-ACCESS  read-write
    STATUS      current
    DESCRIPTION "Source: OPEN-AIR/OSC/Assets/Spectrum/Instrument/bandwidth/Spectrum_Instrument_bandwidth/blocks/Video Bandwidth/vbw_MHz/fader_config"
    ::= { oSCAssetsSpectrumInstrumentBandwidthSpectrumInstrumentbandwie4de 64758 }

oSCAssetsSpectrumInstrumentAmplitudec84e OBJECT IDENTIFIER ::= { oSCAssetsSpectrumInstrumentf0bf 22257 }
oSCAssetsSpectrumInstrumentAmplitudeSpectrumInstrumentamplit6278 OBJECT IDENTIFIER ::= { oSCAssetsSpectrumInstrumentAmplitudec84e 6307 }
oSCAssetsSpectrumInstrumentAmplitudeSpectrumInstrumentamplit1afd OBJECT IDENTIFIER ::= { oSCAssetsSpectrumInstrumentAmplitudeSpectrumInstrumentamplit6278 32595 }
oSCAssetsSpectrumInstrumentAmplitudeSpectrumInstrumentamplitf779 OBJECT IDENTIFIER ::= { oSCAssetsSpectrumInstrumentAmplitudeSpectrumInstrumentamplit1afd 52805 }
oSCAssetsSpectrumInstrumentAmplitudeSpectrumInstrumentamplitfa0b OBJECT IDENTIFIER ::= { oSCAssetsSpectrumInstrumentAmplitudeSpectrumInstrumentamplitf779 23433 }
-- MQTT: OPEN-AIR/OSC/Assets/Spectrum/Instrument/amplitude/Spectrum_Instrument_amplitude/blocks/Reference Level/ref_level_dBm/dial_config
oSCAssetsSpectrumInstrumentAmplitudeSpectrumInstrumentamplitfdcf OBJECT-TYPE
    SYNTAX      DisplayString
    MAX-ACCESS  read-write
    STATUS      current
    DESCRIPTION "Source: OPEN-AIR/OSC/Assets/Spectrum/Instrument/amplitude/Spectrum_Instrument_amplitude/blocks/Reference Level/ref_level_dBm/dial_config"
    ::= { oSCAssetsSpectrumInstrumentAmplitudeSpectrumInstrumentamplitfa0b 49814 }

-- MQTT: OPEN-AIR/OSC/Assets/Spectrum/Instrument/amplitude/Spectrum_Instrument_amplitude/blocks/Reference Level/ref_level_dBm/fader_config
oSCAssetsSpectrumInstrumentAmplitudeSpectrumInstrumentamplit134e OBJECT-TYPE
    SYNTAX      DisplayString
    MAX-ACCESS  read-write
    STATUS      current
    DESCRIPTION "Source: OPEN-AIR/OSC/Assets/Spectrum/Instrument/amplitude/Spectrum_Instrument_amplitude/blocks/Reference Level/ref_level_dBm/fader_config"
    ::= { oSCAssetsSpectrumInstrumentAmplitudeSpectrumInstrumentamplitfa0b 62262 }

oSCAssetsSpectrumInstrumentFrequency859c OBJECT IDENTIFIER ::= { oSCAssetsSpectrumInstrumentf0bf 30451 }
oSCAssetsSpectrumInstrumentFrequencySpectrumInstrumentfreque41d2 OBJECT IDENTIFIER ::= { oSCAssetsSpectrumInstrumentFrequency859c 3403 }
oSCAssetsSpectrumInstrumentFrequencySpectrumInstrumentfrequef1b9 OBJECT IDENTIFIER ::= { oSCAssetsSpectrumInstrumentFrequencySpectrumInstrumentfreque41d2 33772 }
oSCAssetsSpectrumInstrumentFrequencySpectrumInstrumentfreque971f OBJECT IDENTIFIER ::= { oSCAssetsSpectrumInstrumentFrequencySpectrumInstrumentfrequef1b9 20369 }
-- MQTT: OPEN-AIR/OSC/Assets/Spectrum/Instrument/frequency/Spectrum_Instrument_frequency/blocks/Start Stop/stop_freq_MHz
oSCAssetsSpectrumInstrumentFrequencySpectrumInstrumentfrequea149 OBJECT-TYPE
    SYNTAX      DisplayString
    MAX-ACCESS  read-write
    STATUS      current
    DESCRIPTION "Source: OPEN-AIR/OSC/Assets/Spectrum/Instrument/frequency/Spectrum_Instrument_frequency/blocks/Start Stop/stop_freq_MHz"
    ::= { oSCAssetsSpectrumInstrumentFrequencySpectrumInstrumentfreque971f 38775 }

-- MQTT: OPEN-AIR/OSC/Assets/Spectrum/Instrument/frequency/Spectrum_Instrument_frequency/blocks/Start Stop/start_freq_MHz
oSCAssetsSpectrumInstrumentFrequencySpectrumInstrumentfrequeb043 OBJECT-TYPE
    SYNTAX      DisplayString
    MAX-ACCESS  read-write
    STATUS      current
    DESCRIPTION "Source: OPEN-AIR/OSC/Assets/Spectrum/Instrument/frequency/Spectrum_Instrument_frequency/blocks/Start Stop/start_freq_MHz"
    ::= { oSCAssetsSpectrumInstrumentFrequencySpectrumInstrumentfreque971f 61629 }

oSCAssetsSpectrumInstrumentFrequencySpectrumInstrumentfrequee41c OBJECT IDENTIFIER ::= { oSCAssetsSpectrumInstrumentFrequencySpectrumInstrumentfrequef1b9 45314 }
-- MQTT: OPEN-AIR/OSC/Assets/Spectrum/Instrument/frequency/Spectrum_Instrument_frequency/blocks/Frequency/span_freq_MHz
oSCAssetsSpectrumInstrumentFrequencySpectrumInstrumentfrequea0d8 OBJECT-TYPE
    SYNTAX      DisplayString
    MAX-ACCESS  read-write
    STATUS      current
    DESCRIPTION "Source: OPEN-AIR/OSC/Assets/Spectrum/Instrument/frequency/Spectrum_Instrument_frequency/blocks/Frequency/span_freq_MHz"
    ::= { oSCAssetsSpectrumInstrumentFrequencySpectrumInstrumentfrequee41c 29473 }

-- MQTT: OPEN-AIR/OSC/Assets/Spectrum/Instrument/frequency/Spectrum_Instrument_frequency/blocks/Frequency/center_freq_MHz
oSCAssetsSpectrumInstrumentFrequencySpectrumInstrumentfreque22af OBJECT-TYPE
    SYNTAX      DisplayString
    MAX-ACCESS  read-write
    STATUS      current
    DESCRIPTION "Source: OPEN-AIR/OSC/Assets/Spectrum/Instrument/frequency/Spectrum_Instrument_frequency/blocks/Frequency/center_freq_MHz"
    ::= { oSCAssetsSpectrumInstrumentFrequencySpectrumInstrumentfrequee41c 33292 }

oSCAssetsZoofaa0 OBJECT IDENTIFIER ::= { oSCAssetsa5ca 32339 }
oSCAssetsZooMetering477f OBJECT IDENTIFIER ::= { oSCAssetsZoofaa0 1396 }
oSCAssetsZooMeteringBarMeter6ced OBJECT IDENTIFIER ::= { oSCAssetsZooMetering477f 4569 }
oSCAssetsZooMeteringBarMeterREFdb57 OBJECT IDENTIFIER ::= { oSCAssetsZooMeteringBarMeter6ced 6211 }
oSCAssetsZooMeteringBarMeterREFZooMeteringBarMeterREFb2e8 OBJECT IDENTIFIER ::= { oSCAssetsZooMeteringBarMeterREFdb57 166 }
oSCAssetsZooMeteringBarMeterREFZooMeteringBarMeterREFBlocks5012 OBJECT IDENTIFIER ::= { oSCAssetsZooMeteringBarMeterREFZooMeteringBarMeterREFb2e8 20107 }
oSCAssetsZooMeteringBarMeterREFZooMeteringBarMeterREFBlocksA3ba3 OBJECT IDENTIFIER ::= { oSCAssetsZooMeteringBarMeterREFZooMeteringBarMeterREFBlocks5012 33363 }
-- MQTT: OPEN-AIR/OSC/Assets/Zoo/Metering/Bar_Meter/REF/Zoo_Metering_Bar_Meter_REF/blocks/Averaging_Meters_Bar/Standard_VU_Bar
oSCAssetsZooMeteringBarMeterREFZooMeteringBarMeterREFBlocksA2104 OBJECT-TYPE
    SYNTAX      DisplayString
    MAX-ACCESS  read-write
    STATUS      current
    DESCRIPTION "Source: OPEN-AIR/OSC/Assets/Zoo/Metering/Bar_Meter/REF/Zoo_Metering_Bar_Meter_REF/blocks/Averaging_Meters_Bar/Standard_VU_Bar"
    ::= { oSCAssetsZooMeteringBarMeterREFZooMeteringBarMeterREFBlocksA3ba3 10002 }

oSCAssetsZooMeteringBarMeterREFZooMeteringBarMeterREFBlocksPbc7a OBJECT IDENTIFIER ::= { oSCAssetsZooMeteringBarMeterREFZooMeteringBarMeterREFBlocks5012 48575 }
-- MQTT: OPEN-AIR/OSC/Assets/Zoo/Metering/Bar_Meter/REF/Zoo_Metering_Bar_Meter_REF/blocks/Protection_Meters_Bar/PPM_Type_I_Bar
oSCAssetsZooMeteringBarMeterREFZooMeteringBarMeterREFBlocksP1b50 OBJECT-TYPE
    SYNTAX      DisplayString
    MAX-ACCESS  read-write
    STATUS      current
    DESCRIPTION "Source: OPEN-AIR/OSC/Assets/Zoo/Metering/Bar_Meter/REF/Zoo_Metering_Bar_Meter_REF/blocks/Protection_Meters_Bar/PPM_Type_I_Bar"
    ::= { oSCAssetsZooMeteringBarMeterREFZooMeteringBarMeterREFBlocksPbc7a 30192 }

oSCAssetsZooMeteringBarMeterVerticalbar408f OBJECT IDENTIFIER ::= { oSCAssetsZooMeteringBarMeter6ced 21252 }
oSCAssetsZooMeteringBarMeterVerticalbarZooMeteringBarMeterVe80f7 OBJECT IDENTIFIER ::= { oSCAssetsZooMeteringBarMeterVerticalbar408f 63523 }
oSCAssetsZooMeteringBarMeterVerticalbarZooMeteringBarMeterVecb6f OBJECT IDENTIFIER ::= { oSCAssetsZooMeteringBarMeterVerticalbarZooMeteringBarMeterVe80f7 8403 }
oSCAssetsZooMeteringBarMeterVerticalbarZooMeteringBarMeterVe3c62 OBJECT IDENTIFIER ::= { oSCAssetsZooMeteringBarMeterVerticalbarZooMeteringBarMeterVecb6f 33900 }
-- MQTT: OPEN-AIR/OSC/Assets/Zoo/Metering/Bar_Meter/Vertical_bar/Zoo_Metering_Bar_Meter_Vertical_bar/blocks/Wide_Vertical/demo_02_scale_top
oSCAssetsZooMeteringBarMeterVerticalbarZooMeteringBarMeterVeaf80 OBJECT-TYPE
    SYNTAX      DisplayString
    MAX-ACCESS  read-write
    STATUS      current
    DESCRIPTION "Source: OPEN-AIR/OSC/Assets/Zoo/Metering/Bar_Meter/Vertical_bar/Zoo_Metering_Bar_Meter_Vertical_bar/blocks/Wide_Vertical/demo_02_scale_top"
    ::= { oSCAssetsZooMeteringBarMeterVerticalbarZooMeteringBarMeterVe3c62 2216 }

oSCAssetsZooMeteringBarMeterHorizontalbarcd00 OBJECT IDENTIFIER ::= { oSCAssetsZooMeteringBarMeter6ced 42606 }
oSCAssetsZooMeteringBarMeterHorizontalbarZooMeteringBarMeter4234 OBJECT IDENTIFIER ::= { oSCAssetsZooMeteringBarMeterHorizontalbarcd00 58115 }
oSCAssetsZooMeteringBarMeterHorizontalbarZooMeteringBarMeter1f32 OBJECT IDENTIFIER ::= { oSCAssetsZooMeteringBarMeterHorizontalbarZooMeteringBarMeter4234 24465 }
oSCAssetsZooMeteringBarMeterHorizontalbarZooMeteringBarMeter49ea OBJECT IDENTIFIER ::= { oSCAssetsZooMeteringBarMeterHorizontalbarZooMeteringBarMeter1f32 21260 }
-- MQTT: OPEN-AIR/OSC/Assets/Zoo/Metering/Bar_Meter/Horizontal_bar/Zoo_Metering_Bar_Meter_Horizontal_bar/blocks/Wide_Range_tribar_demo/demo_02_scale_top
oSCAssetsZooMeteringBarMeterHorizontalbarZooMeteringBarMeter270f OBJECT-TYPE
    SYNTAX      DisplayString
    MAX-ACCESS  read-write
    STATUS      current
    DESCRIPTION "Source: OPEN-AIR/OSC/Assets/Zoo/Metering/Bar_Meter/Horizontal_bar/Zoo_Metering_Bar_Meter_Horizontal_bar/blocks/Wide_Range_tribar_demo/demo_02_scale_top"
    ::= { oSCAssetsZooMeteringBarMeterHorizontalbarZooMeteringBarMeter49ea 40270 }

-- MQTT: OPEN-AIR/OSC/Assets/Zoo/Metering/Bar_Meter/Horizontal_bar/Zoo_Metering_Bar_Meter_Horizontal_bar/blocks/Wide_Range_tribar_demo/demo_01_standard_bottom
oSCAssetsZooMeteringBarMeterHorizontalbarZooMeteringBarMeterec15 OBJECT-TYPE
    SYNTAX      DisplayString
    MAX-ACCESS  read-write
    STATUS      current
    DESCRIPTION "Source: OPEN-AIR/OSC/Assets/Zoo/Metering/Bar_Meter/Horizontal_bar/Zoo_Metering_Bar_Meter_Horizontal_bar/blocks/Wide_Range_tribar_demo/demo_01_standard_bottom"
    ::= { oSCAssetsZooMeteringBarMeterHorizontalbarZooMeteringBarMeter49ea 43135 }

-- MQTT: OPEN-AIR/OSC/Assets/Zoo/Metering/Bar_Meter/Horizontal_bar/Zoo_Metering_Bar_Meter_Horizontal_bar/blocks/Wide_Range_tribar_demo/demo_03_no_ticks_bottom_text
oSCAssetsZooMeteringBarMeterHorizontalbarZooMeteringBarMeter534e OBJECT-TYPE
    SYNTAX      DisplayString
    MAX-ACCESS  read-write
    STATUS      current
    DESCRIPTION "Source: OPEN-AIR/OSC/Assets/Zoo/Metering/Bar_Meter/Horizontal_bar/Zoo_Metering_Bar_Meter_Horizontal_bar/blocks/Wide_Range_tribar_demo/demo_03_no_ticks_bottom_text"
    ::= { oSCAssetsZooMeteringBarMeterHorizontalbarZooMeteringBarMeter49ea 43166 }

oSCAssetsZooMeteringBarMeterHorizontalTri3e21 OBJECT IDENTIFIER ::= { oSCAssetsZooMeteringBarMeter6ced 61906 }
oSCAssetsZooMeteringBarMeterHorizontalTriZooMeteringBarMeterd1ab OBJECT IDENTIFIER ::= { oSCAssetsZooMeteringBarMeterHorizontalTri3e21 45746 }
oSCAssetsZooMeteringBarMeterHorizontalTriZooMeteringBarMetera241 OBJECT IDENTIFIER ::= { oSCAssetsZooMeteringBarMeterHorizontalTriZooMeteringBarMeterd1ab 15964 }
oSCAssetsZooMeteringBarMeterHorizontalTriZooMeteringBarMetera03a OBJECT IDENTIFIER ::= { oSCAssetsZooMeteringBarMeterHorizontalTriZooMeteringBarMetera241 45017 }
-- MQTT: OPEN-AIR/OSC/Assets/Zoo/Metering/Bar_Meter/Horizontal_Tri/Zoo_Metering_Bar_Meter_Horizontal_Tri/blocks/Wide_Range_Horizontal/demo_01_standard_bottom
oSCAssetsZooMeteringBarMeterHorizontalTriZooMeteringBarMeter31bc OBJECT-TYPE
    SYNTAX      DisplayString
    MAX-ACCESS  read-write
    STATUS      current
    DESCRIPTION "Source: OPEN-AIR/OSC/Assets/Zoo/Metering/Bar_Meter/Horizontal_Tri/Zoo_Metering_Bar_Meter_Horizontal_Tri/blocks/Wide_Range_Horizontal/demo_01_standard_bottom"
    ::= { oSCAssetsZooMeteringBarMeterHorizontalTriZooMeteringBarMetera03a 7629 }

-- MQTT: OPEN-AIR/OSC/Assets/Zoo/Metering/Bar_Meter/Horizontal_Tri/Zoo_Metering_Bar_Meter_Horizontal_Tri/blocks/Wide_Range_Horizontal/demo_02_scale_top
oSCAssetsZooMeteringBarMeterHorizontalTriZooMeteringBarMeterd1d1 OBJECT-TYPE
    SYNTAX      DisplayString
    MAX-ACCESS  read-write
    STATUS      current
    DESCRIPTION "Source: OPEN-AIR/OSC/Assets/Zoo/Metering/Bar_Meter/Horizontal_Tri/Zoo_Metering_Bar_Meter_Horizontal_Tri/blocks/Wide_Range_Horizontal/demo_02_scale_top"
    ::= { oSCAssetsZooMeteringBarMeterHorizontalTriZooMeteringBarMetera03a 9267 }

-- MQTT: OPEN-AIR/OSC/Assets/Zoo/Metering/Bar_Meter/Horizontal_Tri/Zoo_Metering_Bar_Meter_Horizontal_Tri/blocks/Wide_Range_Horizontal/demo_03_no_ticks_bottom_text
oSCAssetsZooMeteringBarMeterHorizontalTriZooMeteringBarMeterf1da OBJECT-TYPE
    SYNTAX      DisplayString
    MAX-ACCESS  read-write
    STATUS      current
    DESCRIPTION "Source: OPEN-AIR/OSC/Assets/Zoo/Metering/Bar_Meter/Horizontal_Tri/Zoo_Metering_Bar_Meter_Horizontal_Tri/blocks/Wide_Range_Horizontal/demo_03_no_ticks_bottom_text"
    ::= { oSCAssetsZooMeteringBarMeterHorizontalTriZooMeteringBarMetera03a 37119 }

-- MQTT: OPEN-AIR/OSC/Assets/Zoo/Metering/Bar_Meter/Horizontal_Tri/Zoo_Metering_Bar_Meter_Horizontal_Tri/blocks/Wide_Range_Horizontal/demo_06_rect_peak_top
oSCAssetsZooMeteringBarMeterHorizontalTriZooMeteringBarMeter4487 OBJECT-TYPE
    SYNTAX      DisplayString
    MAX-ACCESS  read-write
    STATUS      current
    DESCRIPTION "Source: OPEN-AIR/OSC/Assets/Zoo/Metering/Bar_Meter/Horizontal_Tri/Zoo_Metering_Bar_Meter_Horizontal_Tri/blocks/Wide_Range_Horizontal/demo_06_rect_peak_top"
    ::= { oSCAssetsZooMeteringBarMeterHorizontalTriZooMeteringBarMetera03a 41643 }

oSCAssetsZooFaders4ad2 OBJECT IDENTIFIER ::= { oSCAssetsZoofaa0 32786 }
oSCAssetsZooFadersFaderDialc117 OBJECT IDENTIFIER ::= { oSCAssetsZooFaders4ad2 13825 }
oSCAssetsZooFadersFaderDialClassica648 OBJECT IDENTIFIER ::= { oSCAssetsZooFadersFaderDialc117 13054 }
oSCAssetsZooFadersFaderDialClassicZooFadersFaderDialClassicf87f OBJECT IDENTIFIER ::= { oSCAssetsZooFadersFaderDialClassica648 45173 }
oSCAssetsZooFadersFaderDialClassicZooFadersFaderDialClassicB477c OBJECT IDENTIFIER ::= { oSCAssetsZooFadersFaderDialClassicZooFadersFaderDialClassicf87f 1919 }
oSCAssetsZooFadersFaderDialClassicZooFadersFaderDialClassicB34e7 OBJECT IDENTIFIER ::= { oSCAssetsZooFadersFaderDialClassicZooFadersFaderDialClassicB477c 53384 }
oSCAssetsZooFadersFaderDialClassicZooFadersFaderDialClassicB12a8 OBJECT IDENTIFIER ::= { oSCAssetsZooFadersFaderDialClassicZooFadersFaderDialClassicB34e7 35733 }
-- MQTT: OPEN-AIR/OSC/Assets/Zoo/Faders/Fader_Dial/Classic/Zoo_Faders_Fader_Dial_Classic/blocks/elements1/examplefields/dial_config
oSCAssetsZooFadersFaderDialClassicZooFadersFaderDialClassicB3803 OBJECT-TYPE
    SYNTAX      DisplayString
    MAX-ACCESS  read-write
    STATUS      current
    DESCRIPTION "Source: OPEN-AIR/OSC/Assets/Zoo/Faders/Fader_Dial/Classic/Zoo_Faders_Fader_Dial_Classic/blocks/elements1/examplefields/dial_config"
    ::= { oSCAssetsZooFadersFaderDialClassicZooFadersFaderDialClassicB12a8 6257 }

oSCAssetsZooFadersGCAdeca OBJECT IDENTIFIER ::= { oSCAssetsZooFaders4ad2 24572 }
oSCAssetsZooFadersGCA5pointba81 OBJECT IDENTIFIER ::= { oSCAssetsZooFadersGCAdeca 53363 }
oSCAssetsZooFadersGCA5pointZooFadersGCA5point19f64 OBJECT IDENTIFIER ::= { oSCAssetsZooFadersGCA5pointba81 64382 }
oSCAssetsZooFadersGCA5pointZooFadersGCA5point1Blocks9125 OBJECT IDENTIFIER ::= { oSCAssetsZooFadersGCA5pointZooFadersGCA5point19f64 49155 }
oSCAssetsZooFadersGCA5pointZooFadersGCA5point1Blocks5pointOn5948 OBJECT IDENTIFIER ::= { oSCAssetsZooFadersGCA5pointZooFadersGCA5point1Blocks9125 42509 }
oSCAssetsZooFadersGCA5pointZooFadersGCA5point1Blocks5pointOn44c3 OBJECT IDENTIFIER ::= { oSCAssetsZooFadersGCA5pointZooFadersGCA5point1Blocks5pointOn5948 65422 }
-- MQTT: OPEN-AIR/OSC/Assets/Zoo/Faders/GCA/5point/Zoo_Faders_GCA_5point1/blocks/5 point One/composite_drums/ch_1
oSCAssetsZooFadersGCA5pointZooFadersGCA5point1Blocks5pointOn5136 OBJECT-TYPE
    SYNTAX      DisplayString
    MAX-ACCESS  read-write
    STATUS      current
    DESCRIPTION "Source: OPEN-AIR/OSC/Assets/Zoo/Faders/GCA/5point/Zoo_Faders_GCA_5point1/blocks/5 point One/composite_drums/ch_1"
    ::= { oSCAssetsZooFadersGCA5pointZooFadersGCA5point1Blocks5pointOn44c3 26118 }

oSCAssetsZooFadersMDPf6ac OBJECT IDENTIFIER ::= { oSCAssetsZooFaders4ad2 27679 }
oSCAssetsZooFadersMDPZooFadersMDP5fba OBJECT IDENTIFIER ::= { oSCAssetsZooFadersMDPf6ac 7919 }
oSCAssetsZooFadersMDPZooFadersMDPBlocksde9b OBJECT IDENTIFIER ::= { oSCAssetsZooFadersMDPZooFadersMDP5fba 6276 }
oSCAssetsZooFadersMDPZooFadersMDPBlocksMdpdemo982d OBJECT IDENTIFIER ::= { oSCAssetsZooFadersMDPZooFadersMDPBlocksde9b 62819 }
oSCAssetsZooFadersMDPZooFadersMDPBlocksMdpdemoMdp153ed OBJECT IDENTIFIER ::= { oSCAssetsZooFadersMDPZooFadersMDPBlocksMdpdemo982d 53355 }
oSCAssetsZooFadersMDPZooFadersMDPBlocksMdpdemoMdp1Graph75a6 OBJECT IDENTIFIER ::= { oSCAssetsZooFadersMDPZooFadersMDPBlocksMdpdemoMdp153ed 10552 }
oSCAssetsZooFadersMDPZooFadersMDPBlocksMdpdemoMdp1GraphOaDatbeb1 OBJECT IDENTIFIER ::= { oSCAssetsZooFadersMDPZooFadersMDPBlocksMdpdemoMdp1Graph75a6 58044 }
-- MQTT: OPEN-AIR/OSC/Assets/Zoo/Faders/MDP/Zoo_Faders_MDP/blocks/mdp_demo/mdp_1/graph/oaDataRunningFiles/grid_ref
oSCAssetsZooFadersMDPZooFadersMDPBlocksMdpdemoMdp1GraphOaDate8f6 OBJECT-TYPE
    SYNTAX      DisplayString
    MAX-ACCESS  read-write
    STATUS      current
    DESCRIPTION "Source: OPEN-AIR/OSC/Assets/Zoo/Faders/MDP/Zoo_Faders_MDP/blocks/mdp_demo/mdp_1/graph/oaDataRunningFiles/grid_ref"
    ::= { oSCAssetsZooFadersMDPZooFadersMDPBlocksMdpdemoMdp1GraphOaDatbeb1 24994 }

oSCAssetsZooGraphingb079 OBJECT IDENTIFIER ::= { oSCAssetsZoofaa0 34781 }
oSCAssetsZooGraphingXYGraphs6e34 OBJECT IDENTIFIER ::= { oSCAssetsZooGraphingb079 23349 }
oSCAssetsZooGraphingXYGraphsGraphingb3e6 OBJECT IDENTIFIER ::= { oSCAssetsZooGraphingXYGraphs6e34 5563 }
oSCAssetsZooGraphingXYGraphsGraphingZoodatagraphingXYGraphsGd1b3 OBJECT IDENTIFIER ::= { oSCAssetsZooGraphingXYGraphsGraphingb3e6 37061 }
oSCAssetsZooGraphingXYGraphsGraphingZoodatagraphingXYGraphsG917a OBJECT IDENTIFIER ::= { oSCAssetsZooGraphingXYGraphsGraphingZoodatagraphingXYGraphsGd1b3 43143 }
oSCAssetsZooGraphingXYGraphsGraphingZoodatagraphingXYGraphsG203d OBJECT IDENTIFIER ::= { oSCAssetsZooGraphingXYGraphsGraphingZoodatagraphingXYGraphsG917a 4975 }
oSCAssetsZooGraphingXYGraphsGraphingZoodatagraphingXYGraphsG61f2 OBJECT IDENTIFIER ::= { oSCAssetsZooGraphingXYGraphsGraphingZoodatagraphingXYGraphsG203d 52367 }
-- MQTT: OPEN-AIR/OSC/Assets/Zoo/graphing/XY_Graphs/Graphing/Zoo_data_graphing_XY_Graphs_Graphing_3/blocks/All_Features_Plot/oaDataRunningFiles/signal
oSCAssetsZooGraphingXYGraphsGraphingZoodatagraphingXYGraphsGc84d OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/All_Features_Plot/oaDataRunningFiles/signal"
    ::= { oSCAssetsZooGraphingXYGraphsGraphingZoodatagraphingXYGraphsG61f2 30162 }

oSCAssetsZooGraphingXYGraphsGraphingZoodatagraphingXYGraphsGb9be OBJECT IDENTIFIER ::= { oSCAssetsZooGraphingXYGraphsGraphingZoodatagraphingXYGraphsG917a 19194 }
oSCAssetsZooGraphingXYGraphsGraphingZoodatagraphingXYGraphsG34b1 OBJECT IDENTIFIER ::= { oSCAssetsZooGraphingXYGraphsGraphingZoodatagraphingXYGraphsGb9be 56098 }
-- MQTT: OPEN-AIR/OSC/Assets/Zoo/graphing/XY_Graphs/Graphing/Zoo_data_graphing_XY_Graphs_Graphing_3/blocks/Log_Log_Zoom/oaDataRunningFiles/power_law
oSCAssetsZooGraphingXYGraphsGraphingZoodatagraphingXYGraphsGadfe OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Log_Log_Zoom/oaDataRunningFiles/power_law"
    ::= { oSCAssetsZooGraphingXYGraphsGraphingZoodatagraphingXYGraphsG34b1 19122 }

oSCAssetsZooGraphingXYGraphsGraphingZoodatagraphingXYGraphsGe094 OBJECT IDENTIFIER ::= { oSCAssetsZooGraphingXYGraphsGraphingZoodatagraphingXYGraphsG917a 19849 }
oSCAssetsZooGraphingXYGraphsGraphingZoodatagraphingXYGraphsG7aad OBJECT IDENTIFIER ::= { oSCAssetsZooGraphingXYGraphsGraphingZoodatagraphingXYGraphsGe094 56768 }
-- MQTT: OPEN-AIR/OSC/Assets/Zoo/graphing/XY_Graphs/Graphing/Zoo_data_graphing_XY_Graphs_Graphing_3/blocks/Heartbeat_Plot/oaDataRunningFiles/ekg
oSCAssetsZooGraphingXYGraphsGraphingZoodatagraphingXYGraphsGfb46 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Heartbeat_Plot/oaDataRunningFiles/ekg"
    ::= { oSCAssetsZooGraphingXYGraphsGraphingZoodatagraphingXYGraphsG7aad 42637 }

oSCAssetsZooGraphingXYGraphsGraphingZoodatagraphingXYGraphsG5ba2 OBJECT IDENTIFIER ::= { oSCAssetsZooGraphingXYGraphsGraphingZoodatagraphingXYGraphsG917a 26092 }
oSCAssetsZooGraphingXYGraphsGraphingZoodatagraphingXYGraphsG7143 OBJECT IDENTIFIER ::= { oSCAssetsZooGraphingXYGraphsGraphingZoodatagraphingXYGraphsG5ba2 17247 }
-- MQTT: OPEN-AIR/OSC/Assets/Zoo/graphing/XY_Graphs/Graphing/Zoo_data_graphing_XY_Graphs_Graphing_3/blocks/Log_Y_Zoom/oaDataRunningFiles/exp_growth
oSCAssetsZooGraphingXYGraphsGraphingZoodatagraphingXYGraphsGce97 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Log_Y_Zoom/oaDataRunningFiles/exp_growth"
    ::= { oSCAssetsZooGraphingXYGraphsGraphingZoodatagraphingXYGraphsG7143 5906 }

oSCAssetsZooGraphingXYGraphsGraphingZoodatagraphingXYGraphsG8a63 OBJECT IDENTIFIER ::= { oSCAssetsZooGraphingXYGraphsGraphingZoodatagraphingXYGraphsG917a 35887 }
oSCAssetsZooGraphingXYGraphsGraphingZoodatagraphingXYGraphsGee0f OBJECT IDENTIFIER ::= { oSCAssetsZooGraphingXYGraphsGraphingZoodatagraphingXYGraphsG8a63 5868 }
-- MQTT: OPEN-AIR/OSC/Assets/Zoo/graphing/XY_Graphs/Graphing/Zoo_data_graphing_XY_Graphs_Graphing_3/blocks/Spiral_Plot/oaDataRunningFiles/spiral
oSCAssetsZooGraphingXYGraphsGraphingZoodatagraphingXYGraphsG5c3b OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Spiral_Plot/oaDataRunningFiles/spiral"
    ::= { oSCAssetsZooGraphingXYGraphsGraphingZoodatagraphingXYGraphsGee0f 63158 }

oSCAssetsZooGraphingXYGraphsGraphingZoodatagraphingXYGraphsG2f29 OBJECT IDENTIFIER ::= { oSCAssetsZooGraphingXYGraphsGraphingZoodatagraphingXYGraphsG917a 37167 }
oSCAssetsZooGraphingXYGraphsGraphingZoodatagraphingXYGraphsG6df6 OBJECT IDENTIFIER ::= { oSCAssetsZooGraphingXYGraphsGraphingZoodatagraphingXYGraphsG2f29 29741 }
-- MQTT: OPEN-AIR/OSC/Assets/Zoo/graphing/XY_Graphs/Graphing/Zoo_data_graphing_XY_Graphs_Graphing_3/blocks/Multi_Style_Plot/oaDataRunningFiles/data1
oSCAssetsZooGraphingXYGraphsGraphingZoodatagraphingXYGraphsG82b2 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Multi_Style_Plot/oaDataRunningFiles/data1"
    ::= { oSCAssetsZooGraphingXYGraphsGraphingZoodatagraphingXYGraphsG6df6 35860 }

-- MQTT: OPEN-AIR/OSC/Assets/Zoo/graphing/XY_Graphs/Graphing/Zoo_data_graphing_XY_Graphs_Graphing_3/blocks/Multi_Style_Plot/oaDataRunningFiles/data2
oSCAssetsZooGraphingXYGraphsGraphingZoodatagraphingXYGraphsG1bbb OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Multi_Style_Plot/oaDataRunningFiles/data2"
    ::= { oSCAssetsZooGraphingXYGraphsGraphingZoodatagraphingXYGraphsG6df6 56750 }

oSCAssetsZooGraphingXYGraphsGraphingZoodatagraphingXYGraphsG90fe OBJECT IDENTIFIER ::= { oSCAssetsZooGraphingXYGraphsGraphingZoodatagraphingXYGraphsG917a 46665 }
oSCAssetsZooGraphingXYGraphsGraphingZoodatagraphingXYGraphsGd4c8 OBJECT IDENTIFIER ::= { oSCAssetsZooGraphingXYGraphsGraphingZoodatagraphingXYGraphsG90fe 54097 }
-- MQTT: OPEN-AIR/OSC/Assets/Zoo/graphing/XY_Graphs/Graphing/Zoo_data_graphing_XY_Graphs_Graphing_3/blocks/Log_X_Zoom/oaDataRunningFiles/log_decay
oSCAssetsZooGraphingXYGraphsGraphingZoodatagraphingXYGraphsGaffe OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Log_X_Zoom/oaDataRunningFiles/log_decay"
    ::= { oSCAssetsZooGraphingXYGraphsGraphingZoodatagraphingXYGraphsGd4c8 58144 }

oSCAssetsZooGraphingXYGraphsGraphingZoodatagraphingXYGraphsG5cbe OBJECT IDENTIFIER ::= { oSCAssetsZooGraphingXYGraphsGraphingZoodatagraphingXYGraphsG917a 55420 }
oSCAssetsZooGraphingXYGraphsGraphingZoodatagraphingXYGraphsGa985 OBJECT IDENTIFIER ::= { oSCAssetsZooGraphingXYGraphsGraphingZoodatagraphingXYGraphsG5cbe 25630 }
-- MQTT: OPEN-AIR/OSC/Assets/Zoo/graphing/XY_Graphs/Graphing/Zoo_data_graphing_XY_Graphs_Graphing_3/blocks/Scientific_Plot/oaDataRunningFiles/scientific_data
oSCAssetsZooGraphingXYGraphsGraphingZoodatagraphingXYGraphsG8b2c OBJECT-TYPE
    SYNTAX      DisplayString
    MAX-ACCESS  read-write
    STATUS      current
    DESCRIPTION "Source: OPEN-AIR/OSC/Assets/Zoo/graphing/XY_Graphs/Graphing/Zoo_data_graphing_XY_Graphs_Graphing_3/blocks/Scientific_Plot/oaDataRunningFiles/scientific_data"
    ::= { oSCAssetsZooGraphingXYGraphsGraphingZoodatagraphingXYGraphsGa985 36115 }

oSCAssetsZooGraphingXYGraphsGraphingZoodatagraphingXYGraphsGa6b4 OBJECT IDENTIFIER ::= { oSCAssetsZooGraphingXYGraphsGraphingb3e6 41043 }
oSCAssetsZooGraphingXYGraphsGraphingZoodatagraphingXYGraphsG5dd0 OBJECT IDENTIFIER ::= { oSCAssetsZooGraphingXYGraphsGraphingZoodatagraphingXYGraphsGa6b4 43033 }
oSCAssetsZooGraphingXYGraphsGraphingZoodatagraphingXYGraphsGdfab OBJECT IDENTIFIER ::= { oSCAssetsZooGraphingXYGraphsGraphingZoodatagraphingXYGraphsG5dd0 5596 }
oSCAssetsZooGraphingXYGraphsGraphingZoodatagraphingXYGraphsG6497 OBJECT IDENTIFIER ::= { oSCAssetsZooGraphingXYGraphsGraphingZoodatagraphingXYGraphsGdfab 49063 }
-- MQTT: OPEN-AIR/OSC/Assets/Zoo/graphing/XY_Graphs/Graphing/Zoo_data_graphing_XY_Graphs_Graphing_2/blocks/Pulse_Train/oaDataRunningFiles/pulses
oSCAssetsZooGraphingXYGraphsGraphingZoodatagraphingXYGraphsGd6ba OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Pulse_Train/oaDataRunningFiles/pulses"
    ::= { oSCAssetsZooGraphingXYGraphsGraphingZoodatagraphingXYGraphsG6497 695 }

oSCAssetsZooGraphingXYGraphsGraphingZoodatagraphingXYGraphsG2aad OBJECT IDENTIFIER ::= { oSCAssetsZooGraphingXYGraphsGraphingZoodatagraphingXYGraphsG5dd0 9547 }
oSCAssetsZooGraphingXYGraphsGraphingZoodatagraphingXYGraphsG8ae9 OBJECT IDENTIFIER ::= { oSCAssetsZooGraphingXYGraphsGraphingZoodatagraphingXYGraphsG2aad 1901 }
-- MQTT: OPEN-AIR/OSC/Assets/Zoo/graphing/XY_Graphs/Graphing/Zoo_data_graphing_XY_Graphs_Graphing_2/blocks/Matrix_Scatter/oaDataRunningFiles/matrix_dots
oSCAssetsZooGraphingXYGraphsGraphingZoodatagraphingXYGraphsG66e9 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Matrix_Scatter/oaDataRunningFiles/matrix_dots"
    ::= { oSCAssetsZooGraphingXYGraphsGraphingZoodatagraphingXYGraphsG8ae9 18449 }

oSCAssetsZooGraphingXYGraphsGraphingZoodatagraphingXYGraphsG6c2b OBJECT IDENTIFIER ::= { oSCAssetsZooGraphingXYGraphsGraphingZoodatagraphingXYGraphsG5dd0 16346 }
oSCAssetsZooGraphingXYGraphsGraphingZoodatagraphingXYGraphsG8829 OBJECT IDENTIFIER ::= { oSCAssetsZooGraphingXYGraphsGraphingZoodatagraphingXYGraphsG6c2b 7686 }
-- MQTT: OPEN-AIR/OSC/Assets/Zoo/graphing/XY_Graphs/Graphing/Zoo_data_graphing_XY_Graphs_Graphing_2/blocks/Cubic_Plot/oaDataRunningFiles/x_cubed
oSCAssetsZooGraphingXYGraphsGraphingZoodatagraphingXYGraphsGace5 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Cubic_Plot/oaDataRunningFiles/x_cubed"
    ::= { oSCAssetsZooGraphingXYGraphsGraphingZoodatagraphingXYGraphsG8829 45722 }

oSCAssetsZooGraphingXYGraphsGraphingZoodatagraphingXYGraphsG812d OBJECT IDENTIFIER ::= { oSCAssetsZooGraphingXYGraphsGraphingZoodatagraphingXYGraphsG5dd0 17275 }
oSCAssetsZooGraphingXYGraphsGraphingZoodatagraphingXYGraphsGfd0d OBJECT IDENTIFIER ::= { oSCAssetsZooGraphingXYGraphsGraphingZoodatagraphingXYGraphsG812d 18554 }
-- MQTT: OPEN-AIR/OSC/Assets/Zoo/graphing/XY_Graphs/Graphing/Zoo_data_graphing_XY_Graphs_Graphing_2/blocks/Inverse_Plot/oaDataRunningFiles/inverse_x
oSCAssetsZooGraphingXYGraphsGraphingZoodatagraphingXYGraphsG7208 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Inverse_Plot/oaDataRunningFiles/inverse_x"
    ::= { oSCAssetsZooGraphingXYGraphsGraphingZoodatagraphingXYGraphsGfd0d 14752 }

oSCAssetsZooGraphingXYGraphsGraphingZoodatagraphingXYGraphsG7535 OBJECT IDENTIFIER ::= { oSCAssetsZooGraphingXYGraphsGraphingZoodatagraphingXYGraphsG5dd0 18723 }
oSCAssetsZooGraphingXYGraphsGraphingZoodatagraphingXYGraphsG1e88 OBJECT IDENTIFIER ::= { oSCAssetsZooGraphingXYGraphsGraphingZoodatagraphingXYGraphsG7535 33755 }
-- MQTT: OPEN-AIR/OSC/Assets/Zoo/graphing/XY_Graphs/Graphing/Zoo_data_graphing_XY_Graphs_Graphing_2/blocks/Square_Root_Plot/oaDataRunningFiles/sqrt_x
oSCAssetsZooGraphingXYGraphsGraphingZoodatagraphingXYGraphsG1c1e OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Square_Root_Plot/oaDataRunningFiles/sqrt_x"
    ::= { oSCAssetsZooGraphingXYGraphsGraphingZoodatagraphingXYGraphsG1e88 55843 }

oSCAssetsZooGraphingXYGraphsGraphingZoodatagraphingXYGraphsG3d0a OBJECT IDENTIFIER ::= { oSCAssetsZooGraphingXYGraphsGraphingZoodatagraphingXYGraphsG5dd0 25325 }
oSCAssetsZooGraphingXYGraphsGraphingZoodatagraphingXYGraphsG5f60 OBJECT IDENTIFIER ::= { oSCAssetsZooGraphingXYGraphsGraphingZoodatagraphingXYGraphsG3d0a 39820 }
-- MQTT: OPEN-AIR/OSC/Assets/Zoo/graphing/XY_Graphs/Graphing/Zoo_data_graphing_XY_Graphs_Graphing_2/blocks/Another_Log_Plot/oaDataRunningFiles/log_data_2
oSCAssetsZooGraphingXYGraphsGraphingZoodatagraphingXYGraphsGc20f OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Another_Log_Plot/oaDataRunningFiles/log_data_2"
    ::= { oSCAssetsZooGraphingXYGraphsGraphingZoodatagraphingXYGraphsG5f60 29044 }

oSCAssetsZooGraphingXYGraphsGraphingZoodatagraphingXYGraphsG74ab OBJECT IDENTIFIER ::= { oSCAssetsZooGraphingXYGraphsGraphingZoodatagraphingXYGraphsG5dd0 29567 }
oSCAssetsZooGraphingXYGraphsGraphingZoodatagraphingXYGraphsG83fa OBJECT IDENTIFIER ::= { oSCAssetsZooGraphingXYGraphsGraphingZoodatagraphingXYGraphsG74ab 24235 }
-- MQTT: OPEN-AIR/OSC/Assets/Zoo/graphing/XY_Graphs/Graphing/Zoo_data_graphing_XY_Graphs_Graphing_2/blocks/Damped_Sine_Wave/oaDataRunningFiles/damped_sine
oSCAssetsZooGraphingXYGraphsGraphingZoodatagraphingXYGraphsGbdbc OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Damped_Sine_Wave/oaDataRunningFiles/damped_sine"
    ::= { oSCAssetsZooGraphingXYGraphsGraphingZoodatagraphingXYGraphsG83fa 25512 }

oSCAssetsZooGraphingXYGraphsGraphingZoodatagraphingXYGraphsGe8f9 OBJECT IDENTIFIER ::= { oSCAssetsZooGraphingXYGraphsGraphingZoodatagraphingXYGraphsG5dd0 52560 }
oSCAssetsZooGraphingXYGraphsGraphingZoodatagraphingXYGraphsGa191 OBJECT IDENTIFIER ::= { oSCAssetsZooGraphingXYGraphsGraphingZoodatagraphingXYGraphsGe8f9 49853 }
-- MQTT: OPEN-AIR/OSC/Assets/Zoo/graphing/XY_Graphs/Graphing/Zoo_data_graphing_XY_Graphs_Graphing_2/blocks/Quadratic_Plot/oaDataRunningFiles/x_squared
oSCAssetsZooGraphingXYGraphsGraphingZoodatagraphingXYGraphsGdf18 OBJECT-TYPE
    SYNTAX      DisplayString
    MAX-ACCESS  read-write
    STATUS      current
    DESCRIPTION "Source: OPEN-AIR/OSC/Assets/Zoo/graphing/XY_Graphs/Graphing/Zoo_data_graphing_XY_Graphs_Graphing_2/blocks/Quadratic_Plot/oaDataRunningFiles/x_squared"
    ::= { oSCAssetsZooGraphingXYGraphsGraphingZoodatagraphingXYGraphsGa191 39656 }

oSCAssetsZooGraphingXYGraphsGraphingBlocks28cf OBJECT IDENTIFIER ::= { oSCAssetsZooGraphingXYGraphsGraphingb3e6 63913 }
oSCAssetsZooGraphingXYGraphsGraphingBlocksSunsetPlot7931 OBJECT IDENTIFIER ::= { oSCAssetsZooGraphingXYGraphsGraphingBlocks28cf 1790 }
oSCAssetsZooGraphingXYGraphsGraphingBlocksSunsetPlotOaDataRu7520 OBJECT IDENTIFIER ::= { oSCAssetsZooGraphingXYGraphsGraphingBlocksSunsetPlot7931 15513 }
-- MQTT: OPEN-AIR/OSC/Assets/Zoo/graphing/XY_Graphs/Graphing/blocks/Sunset_Plot/oaDataRunningFiles/hill1
oSCAssetsZooGraphingXYGraphsGraphingBlocksSunsetPlotOaDataRuddbf OBJECT-TYPE
    SYNTAX      DisplayString
    MAX-ACCESS  read-write
    STATUS      current
    DESCRIPTION "Source: OPEN-AIR/OSC/Assets/Zoo/graphing/XY_Graphs/Graphing/blocks/Sunset_Plot/oaDataRunningFiles/hill1"
    ::= { oSCAssetsZooGraphingXYGraphsGraphingBlocksSunsetPlotOaDataRu7520 37657 }

-- MQTT: OPEN-AIR/OSC/Assets/Zoo/graphing/XY_Graphs/Graphing/blocks/Sunset_Plot/oaDataRunningFiles/hill2
oSCAssetsZooGraphingXYGraphsGraphingBlocksSunsetPlotOaDataRu44b6 OBJECT-TYPE
    SYNTAX      DisplayString
    MAX-ACCESS  read-write
    STATUS      current
    DESCRIPTION "Source: OPEN-AIR/OSC/Assets/Zoo/graphing/XY_Graphs/Graphing/blocks/Sunset_Plot/oaDataRunningFiles/hill2"
    ::= { oSCAssetsZooGraphingXYGraphsGraphingBlocksSunsetPlotOaDataRu7520 49827 }

oSCAssetsZooGraphingXYGraphsGraphingBlocksOceanPlot3d44 OBJECT IDENTIFIER ::= { oSCAssetsZooGraphingXYGraphsGraphingBlocks28cf 28914 }
oSCAssetsZooGraphingXYGraphsGraphingBlocksOceanPlotOaDataRun38a8 OBJECT IDENTIFIER ::= { oSCAssetsZooGraphingXYGraphsGraphingBlocksOceanPlot3d44 40113 }
-- MQTT: OPEN-AIR/OSC/Assets/Zoo/graphing/XY_Graphs/Graphing/blocks/Ocean_Plot/oaDataRunningFiles/wave1
oSCAssetsZooGraphingXYGraphsGraphingBlocksOceanPlotOaDataRunf1bf OBJECT-TYPE
    SYNTAX      DisplayString
    MAX-ACCESS  read-write
    STATUS      current
    DESCRIPTION "Source: OPEN-AIR/OSC/Assets/Zoo/graphing/XY_Graphs/Graphing/blocks/Ocean_Plot/oaDataRunningFiles/wave1"
    ::= { oSCAssetsZooGraphingXYGraphsGraphingBlocksOceanPlotOaDataRun38a8 48832 }

oSCAssetsZooGraphingXYGraphsGraphingBlocksBlueprintPlot47a1 OBJECT IDENTIFIER ::= { oSCAssetsZooGraphingXYGraphsGraphingBlocks28cf 51006 }
oSCAssetsZooGraphingXYGraphsGraphingBlocksBlueprintPlotOaDat25ca OBJECT IDENTIFIER ::= { oSCAssetsZooGraphingXYGraphsGraphingBlocksBlueprintPlot47a1 51516 }
-- MQTT: OPEN-AIR/OSC/Assets/Zoo/graphing/XY_Graphs/Graphing/blocks/Blueprint_Plot/oaDataRunningFiles/blueprint_line
oSCAssetsZooGraphingXYGraphsGraphingBlocksBlueprintPlotOaDatcb7b OBJECT-TYPE
    SYNTAX      DisplayString
    MAX-ACCESS  read-write
    STATUS      current
    DESCRIPTION "Source: OPEN-AIR/OSC/Assets/Zoo/graphing/XY_Graphs/Graphing/blocks/Blueprint_Plot/oaDataRunningFiles/blueprint_line"
    ::= { oSCAssetsZooGraphingXYGraphsGraphingBlocksBlueprintPlotOaDat25ca 5515 }

oSCAssetsZooGraphingXYGraphsBargraphde93 OBJECT IDENTIFIER ::= { oSCAssetsZooGraphingXYGraphs6e34 19493 }
oSCAssetsZooGraphingXYGraphsBargraphZoodatagraphingXYGraphsB65a9 OBJECT IDENTIFIER ::= { oSCAssetsZooGraphingXYGraphsBargraphde93 59231 }
oSCAssetsZooGraphingXYGraphsBargraphZoodatagraphingXYGraphsB74a5 OBJECT IDENTIFIER ::= { oSCAssetsZooGraphingXYGraphsBargraphZoodatagraphingXYGraphsB65a9 60002 }
oSCAssetsZooGraphingXYGraphsBargraphZoodatagraphingXYGraphsB7f8c OBJECT IDENTIFIER ::= { oSCAssetsZooGraphingXYGraphsBargraphZoodatagraphingXYGraphsB74a5 41597 }
oSCAssetsZooGraphingXYGraphsBargraphZoodatagraphingXYGraphsBe3d8 OBJECT IDENTIFIER ::= { oSCAssetsZooGraphingXYGraphsBargraphZoodatagraphingXYGraphsB7f8c 62178 }
oSCAssetsZooGraphingXYGraphsBargraphZoodatagraphingXYGraphsB6491 OBJECT IDENTIFIER ::= { oSCAssetsZooGraphingXYGraphsBargraphZoodatagraphingXYGraphsBe3d8 35426 }
oSCAssetsZooGraphingXYGraphsBargraphZoodatagraphingXYGraphsBd56a OBJECT IDENTIFIER ::= { oSCAssetsZooGraphingXYGraphsBargraphZoodatagraphingXYGraphsB6491 54778 }
-- MQTT: OPEN-AIR/OSC/Assets/Zoo/graphing/XY_Graphs/Bar_graph/Zoo_data_graphing_XY_Graphs_Bar_graph/blocks/elements/bar_graph_examples/simple_bar_graph/oaDataRunningFiles/ds_usage
oSCAssetsZooGraphingXYGraphsBargraphZoodatagraphingXYGraphsBf961 OBJECT-TYPE
    SYNTAX      DisplayString
    MAX-ACCESS  read-write
    STATUS      current
    DESCRIPTION "Source: OPEN-AIR/OSC/Assets/Zoo/graphing/XY_Graphs/Bar_graph/Zoo_data_graphing_XY_Graphs_Bar_graph/blocks/elements/bar_graph_examples/simple_bar_graph/oaDataRunningFiles/ds_usage"
    ::= { oSCAssetsZooGraphingXYGraphsBargraphZoodatagraphingXYGraphsBd56a 33071 }

oSCAssetsZooGraphingXYGraphsDynamicgraph3fb7 OBJECT IDENTIFIER ::= { oSCAssetsZooGraphingXYGraphs6e34 48514 }
oSCAssetsZooGraphingXYGraphsDynamicgraphZoodatagraphingXYGrac142 OBJECT IDENTIFIER ::= { oSCAssetsZooGraphingXYGraphsDynamicgraph3fb7 5843 }
oSCAssetsZooGraphingXYGraphsDynamicgraphZoodatagraphingXYGra78d0 OBJECT IDENTIFIER ::= { oSCAssetsZooGraphingXYGraphsDynamicgraphZoodatagraphingXYGrac142 55492 }
oSCAssetsZooGraphingXYGraphsDynamicgraphZoodatagraphingXYGrae648 OBJECT IDENTIFIER ::= { oSCAssetsZooGraphingXYGraphsDynamicgraphZoodatagraphingXYGra78d0 13036 }
oSCAssetsZooGraphingXYGraphsDynamicgraphZoodatagraphingXYGrad10e OBJECT IDENTIFIER ::= { oSCAssetsZooGraphingXYGraphsDynamicgraphZoodatagraphingXYGrae648 53616 }
oSCAssetsZooGraphingXYGraphsDynamicgraphZoodatagraphingXYGrac48a OBJECT IDENTIFIER ::= { oSCAssetsZooGraphingXYGraphsDynamicgraphZoodatagraphingXYGrad10e 19260 }
oSCAssetsZooGraphingXYGraphsDynamicgraphZoodatagraphingXYGradf02 OBJECT IDENTIFIER ::= { oSCAssetsZooGraphingXYGraphsDynamicgraphZoodatagraphingXYGrac48a 12192 }
-- MQTT: OPEN-AIR/OSC/Assets/Zoo/graphing/XY_Graphs/dynamic_graph/Zoo_data_graphing_XY_Graphs_dynamic_graph_2/blocks/elements/dynamic_graph_examples/step_graph/oaDataRunningFiles/logic_signal
oSCAssetsZooGraphingXYGraphsDynamicgraphZoodatagraphingXYGrafd4e OBJECT-TYPE
    SYNTAX      DisplayString
    MAX-ACCESS  read-write
    STATUS      current
    DESCRIPTION "Source: OPEN-AIR/OSC/Assets/Zoo/graphing/XY_Graphs/dynamic_graph/Zoo_data_graphing_XY_Graphs_dynamic_graph_2/blocks/elements/dynamic_graph_examples/step_graph/oaDataRunningFiles/logic_signal"
    ::= { oSCAssetsZooGraphingXYGraphsDynamicgraphZoodatagraphingXYGradf02 32548 }

oSCAssetsZooGraphingXYGraphsDynamicgraphZoodatagraphingXYGrafb3a OBJECT IDENTIFIER ::= { oSCAssetsZooGraphingXYGraphsDynamicgraphZoodatagraphingXYGrad10e 34844 }
oSCAssetsZooGraphingXYGraphsDynamicgraphZoodatagraphingXYGra2998 OBJECT IDENTIFIER ::= { oSCAssetsZooGraphingXYGraphsDynamicgraphZoodatagraphingXYGrafb3a 20609 }
-- MQTT: OPEN-AIR/OSC/Assets/Zoo/graphing/XY_Graphs/dynamic_graph/Zoo_data_graphing_XY_Graphs_dynamic_graph_2/blocks/elements/dynamic_graph_examples/log_demo_graph/oaDataRunningFiles/exp_growth
oSCAssetsZooGraphingXYGraphsDynamicgraphZoodatagraphingXYGra4fb6 OBJECT-TYPE
    SYNTAX      DisplayString
    MAX-ACCESS  read-write
    STATUS      current
    DESCRIPTION "Source: OPEN-AIR/OSC/Assets/Zoo/graphing/XY_Graphs/dynamic_graph/Zoo_data_graphing_XY_Graphs_dynamic_graph_2/blocks/elements/dynamic_graph_examples/log_demo_graph/oaDataRunningFiles/exp_growth"
    ::= { oSCAssetsZooGraphingXYGraphsDynamicgraphZoodatagraphingXYGra2998 55763 }

-- MQTT: OPEN-AIR/OSC/Assets/Zoo/graphing/XY_Graphs/dynamic_graph/Zoo_data_graphing_XY_Graphs_dynamic_graph_2/blocks/elements/dynamic_graph_examples/log_demo_graph/oaDataRunningFiles/power_law
oSCAssetsZooGraphingXYGraphsDynamicgraphZoodatagraphingXYGraeba1 OBJECT-TYPE
    SYNTAX      DisplayString
    MAX-ACCESS  read-write
    STATUS      current
    DESCRIPTION "Source: OPEN-AIR/OSC/Assets/Zoo/graphing/XY_Graphs/dynamic_graph/Zoo_data_graphing_XY_Graphs_dynamic_graph_2/blocks/elements/dynamic_graph_examples/log_demo_graph/oaDataRunningFiles/power_law"
    ::= { oSCAssetsZooGraphingXYGraphsDynamicgraphZoodatagraphingXYGra2998 57729 }

oSCAssetsZooGraphingRadarb48c OBJECT IDENTIFIER ::= { oSCAssetsZooGraphingb079 28406 }
oSCAssetsZooGraphingRadarSample3706 OBJECT IDENTIFIER ::= { oSCAssetsZooGraphingRadarb48c 42236 }
oSCAssetsZooGraphingRadarSampleZoodatagraphingradarSamplea9d4 OBJECT IDENTIFIER ::= { oSCAssetsZooGraphingRadarSample3706 5452 }
oSCAssetsZooGraphingRadarSampleZoodatagraphingradarSampleBlo4710 OBJECT IDENTIFIER ::= { oSCAssetsZooGraphingRadarSampleZoodatagraphingradarSamplea9d4 41443 }
oSCAssetsZooGraphingRadarSampleZoodatagraphingradarSampleBlob2e7 OBJECT IDENTIFIER ::= { oSCAssetsZooGraphingRadarSampleZoodatagraphingradarSampleBlo4710 56140 }
-- MQTT: OPEN-AIR/OSC/Assets/Zoo/graphing/radar/Sample/Zoo_data_graphing_radar_Sample_/blocks/Radar_Eye_Zoo_1/radar_eye_1
oSCAssetsZooGraphingRadarSampleZoodatagraphingradarSampleBlodd45 OBJECT-TYPE
    SYNTAX      DisplayString
    MAX-ACCESS  read-write
    STATUS      current
    DESCRIPTION "Source: OPEN-AIR/OSC/Assets/Zoo/graphing/radar/Sample/Zoo_data_graphing_radar_Sample_/blocks/Radar_Eye_Zoo_1/radar_eye_1"
    ::= { oSCAssetsZooGraphingRadarSampleZoodatagraphingradarSampleBlob2e7 14827 }

oSCAssetsZooGraphingRadarSampleZoodatagraphingradarSample1fc1f OBJECT IDENTIFIER ::= { oSCAssetsZooGraphingRadarSample3706 13849 }
oSCAssetsZooGraphingRadarSampleZoodatagraphingradarSample1Bld5d3 OBJECT IDENTIFIER ::= { oSCAssetsZooGraphingRadarSampleZoodatagraphingradarSample1fc1f 13873 }
oSCAssetsZooGraphingRadarSampleZoodatagraphingradarSample1Bl3a11 OBJECT IDENTIFIER ::= { oSCAssetsZooGraphingRadarSampleZoodatagraphingradarSample1Bld5d3 55036 }
-- MQTT: OPEN-AIR/OSC/Assets/Zoo/graphing/radar/Sample/Zoo_data_graphing_radar_Sample_1/blocks/Radar_Eye_Zoo/radar_eye_2
oSCAssetsZooGraphingRadarSampleZoodatagraphingradarSample1Bl3be9 OBJECT-TYPE
    SYNTAX      DisplayString
    MAX-ACCESS  read-write
    STATUS      current
    DESCRIPTION "Source: OPEN-AIR/OSC/Assets/Zoo/graphing/radar/Sample/Zoo_data_graphing_radar_Sample_1/blocks/Radar_Eye_Zoo/radar_eye_2"
    ::= { oSCAssetsZooGraphingRadarSampleZoodatagraphingradarSample1Bl3a11 8763 }

-- MQTT: OPEN-AIR/OSC/Assets/Zoo/graphing/radar/Sample/Zoo_data_graphing_radar_Sample_1/blocks/Radar_Eye_Zoo/radar_eye_5
oSCAssetsZooGraphingRadarSampleZoodatagraphingradarSample1Bla58d OBJECT-TYPE
    SYNTAX      DisplayString
    MAX-ACCESS  read-write
    STATUS      current
    DESCRIPTION "Source: OPEN-AIR/OSC/Assets/Zoo/graphing/radar/Sample/Zoo_data_graphing_radar_Sample_1/blocks/Radar_Eye_Zoo/radar_eye_5"
    ::= { oSCAssetsZooGraphingRadarSampleZoodatagraphingradarSample1Bl3a11 47000 }

oSCAssetsZooGraphingRadarSampleZoodatagraphingradarSample31211 OBJECT IDENTIFIER ::= { oSCAssetsZooGraphingRadarSample3706 22325 }
oSCAssetsZooGraphingRadarSampleZoodatagraphingradarSample3Bl97f6 OBJECT IDENTIFIER ::= { oSCAssetsZooGraphingRadarSampleZoodatagraphingradarSample31211 12620 }
oSCAssetsZooGraphingRadarSampleZoodatagraphingradarSample3Blcda8 OBJECT IDENTIFIER ::= { oSCAssetsZooGraphingRadarSampleZoodatagraphingradarSample3Bl97f6 7484 }
-- MQTT: OPEN-AIR/OSC/Assets/Zoo/graphing/radar/Sample/Zoo_data_graphing_radar_Sample_3/blocks/Radar_Eye_Zoo_3/radar_eye_3
oSCAssetsZooGraphingRadarSampleZoodatagraphingradarSample3Bl1eb6 OBJECT-TYPE
    SYNTAX      DisplayString
    MAX-ACCESS  read-write
    STATUS      current
    DESCRIPTION "Source: OPEN-AIR/OSC/Assets/Zoo/graphing/radar/Sample/Zoo_data_graphing_radar_Sample_3/blocks/Radar_Eye_Zoo_3/radar_eye_3"
    ::= { oSCAssetsZooGraphingRadarSampleZoodatagraphingradarSample3Blcda8 28457 }

oSCAssetsZooGraphingRadarSampleZoodatagraphingradarSample26516 OBJECT IDENTIFIER ::= { oSCAssetsZooGraphingRadarSample3706 26531 }
oSCAssetsZooGraphingRadarSampleZoodatagraphingradarSample2Bl5b5c OBJECT IDENTIFIER ::= { oSCAssetsZooGraphingRadarSampleZoodatagraphingradarSample26516 12754 }
oSCAssetsZooGraphingRadarSampleZoodatagraphingradarSample2Bl3b8a OBJECT IDENTIFIER ::= { oSCAssetsZooGraphingRadarSampleZoodatagraphingradarSample2Bl5b5c 18573 }
-- MQTT: OPEN-AIR/OSC/Assets/Zoo/graphing/radar/Sample/Zoo_data_graphing_radar_Sample_2/blocks/Radar_Eye_Zoo_2/radar_eye_1
oSCAssetsZooGraphingRadarSampleZoodatagraphingradarSample2Blb85e OBJECT-TYPE
    SYNTAX      DisplayString
    MAX-ACCESS  read-write
    STATUS      current
    DESCRIPTION "Source: OPEN-AIR/OSC/Assets/Zoo/graphing/radar/Sample/Zoo_data_graphing_radar_Sample_2/blocks/Radar_Eye_Zoo_2/radar_eye_1"
    ::= { oSCAssetsZooGraphingRadarSampleZoodatagraphingradarSample2Bl3b8a 789 }

-- MQTT: OPEN-AIR/OSC/Assets/Zoo/graphing/radar/Sample/Zoo_data_graphing_radar_Sample_2/blocks/Radar_Eye_Zoo_2/radar_eye_2
oSCAssetsZooGraphingRadarSampleZoodatagraphingradarSample2Bl2157 OBJECT-TYPE
    SYNTAX      DisplayString
    MAX-ACCESS  read-write
    STATUS      current
    DESCRIPTION "Source: OPEN-AIR/OSC/Assets/Zoo/graphing/radar/Sample/Zoo_data_graphing_radar_Sample_2/blocks/Radar_Eye_Zoo_2/radar_eye_2"
    ::= { oSCAssetsZooGraphingRadarSampleZoodatagraphingradarSample2Bl3b8a 21167 }

oSCAssetsZooGraphingRadarSampleZoodatagraphingradarSample48c75 OBJECT IDENTIFIER ::= { oSCAssetsZooGraphingRadarSample3706 49814 }
oSCAssetsZooGraphingRadarSampleZoodatagraphingradarSample4Bl9d33 OBJECT IDENTIFIER ::= { oSCAssetsZooGraphingRadarSampleZoodatagraphingradarSample48c75 14421 }
oSCAssetsZooGraphingRadarSampleZoodatagraphingradarSample4Bl62d4 OBJECT IDENTIFIER ::= { oSCAssetsZooGraphingRadarSampleZoodatagraphingradarSample4Bl9d33 49128 }
-- MQTT: OPEN-AIR/OSC/Assets/Zoo/graphing/radar/Sample/Zoo_data_graphing_radar_Sample_4/blocks/Radar_Eye_Zoo_4/radar_02
oSCAssetsZooGraphingRadarSampleZoodatagraphingradarSample4Bl6a0d OBJECT-TYPE
    SYNTAX      DisplayString
    MAX-ACCESS  read-write
    STATUS      current
    DESCRIPTION "Source: OPEN-AIR/OSC/Assets/Zoo/graphing/radar/Sample/Zoo_data_graphing_radar_Sample_4/blocks/Radar_Eye_Zoo_4/radar_02"
    ::= { oSCAssetsZooGraphingRadarSampleZoodatagraphingradarSample4Bl62d4 37831 }

-- MQTT: OPEN-AIR/OSC/Assets/Zoo/graphing/radar/Sample/Zoo_data_graphing_radar_Sample_4/blocks/Radar_Eye_Zoo_4/radar_01
oSCAssetsZooGraphingRadarSampleZoodatagraphingradarSample4Blf304 OBJECT-TYPE
    SYNTAX      DisplayString
    MAX-ACCESS  read-write
    STATUS      current
    DESCRIPTION "Source: OPEN-AIR/OSC/Assets/Zoo/graphing/radar/Sample/Zoo_data_graphing_radar_Sample_4/blocks/Radar_Eye_Zoo_4/radar_01"
    ::= { oSCAssetsZooGraphingRadarSampleZoodatagraphingradarSample4Bl62d4 49789 }

oSCAssetsZooKnobs96af OBJECT IDENTIFIER ::= { oSCAssetsZoofaa0 48742 }
oSCAssetsZooKnobsKnobs32a3 OBJECT IDENTIFIER ::= { oSCAssetsZooKnobs96af 58033 }
oSCAssetsZooKnobsKnobsGearknobs9ec6 OBJECT IDENTIFIER ::= { oSCAssetsZooKnobsKnobs32a3 16366 }
oSCAssetsZooKnobsKnobsGearknobsZooKnobsknobsGearknobsca70 OBJECT IDENTIFIER ::= { oSCAssetsZooKnobsKnobsGearknobs9ec6 17556 }
oSCAssetsZooKnobsKnobsGearknobsZooKnobsknobsGearknobsBlocksb4da OBJECT IDENTIFIER ::= { oSCAssetsZooKnobsKnobsGearknobsZooKnobsknobsGearknobsca70 22056 }
oSCAssetsZooKnobsKnobsGearknobsZooKnobsknobsGearknobsBlocksKfcba OBJECT IDENTIFIER ::= { oSCAssetsZooKnobsKnobsGearknobsZooKnobsknobsGearknobsBlocksb4da 15199 }
-- MQTT: OPEN-AIR/OSC/Assets/Zoo/Knobs/knobs/Gear_knobs/Zoo_Knobs_knobs_Gear_knobs/blocks/Knob_Showcase_Gear_Advanced/gear_06
oSCAssetsZooKnobsKnobsGearknobsZooKnobsknobsGearknobsBlocksK51d3 OBJECT-TYPE
    SYNTAX      DisplayString
    MAX-ACCESS  read-write
    STATUS      current
    DESCRIPTION "Source: OPEN-AIR/OSC/Assets/Zoo/Knobs/knobs/Gear_knobs/Zoo_Knobs_knobs_Gear_knobs/blocks/Knob_Showcase_Gear_Advanced/gear_06"
    ::= { oSCAssetsZooKnobsKnobsGearknobsZooKnobsknobsGearknobsBlocksKfcba 8849 }

-- MQTT: OPEN-AIR/OSC/Assets/Zoo/Knobs/knobs/Gear_knobs/Zoo_Knobs_knobs_Gear_knobs/blocks/Knob_Showcase_Gear_Advanced/gear_04
oSCAssetsZooKnobsKnobsGearknobsZooKnobsknobsGearknobsBlocksKbfdd OBJECT-TYPE
    SYNTAX      DisplayString
    MAX-ACCESS  read-write
    STATUS      current
    DESCRIPTION "Source: OPEN-AIR/OSC/Assets/Zoo/Knobs/knobs/Gear_knobs/Zoo_Knobs_knobs_Gear_knobs/blocks/Knob_Showcase_Gear_Advanced/gear_04"
    ::= { oSCAssetsZooKnobsKnobsGearknobsZooKnobsknobsGearknobsBlocksKfcba 17341 }

-- MQTT: OPEN-AIR/OSC/Assets/Zoo/Knobs/knobs/Gear_knobs/Zoo_Knobs_knobs_Gear_knobs/blocks/Knob_Showcase_Gear_Advanced/gear_14
oSCAssetsZooKnobsKnobsGearknobsZooKnobsknobsGearknobsBlocksKa6c6 OBJECT-TYPE
    SYNTAX      DisplayString
    MAX-ACCESS  read-write
    STATUS      current
    DESCRIPTION "Source: OPEN-AIR/OSC/Assets/Zoo/Knobs/knobs/Gear_knobs/Zoo_Knobs_knobs_Gear_knobs/blocks/Knob_Showcase_Gear_Advanced/gear_14"
    ::= { oSCAssetsZooKnobsKnobsGearknobsZooKnobsknobsGearknobsBlocksKfcba 29436 }

-- MQTT: OPEN-AIR/OSC/Assets/Zoo/Knobs/knobs/Gear_knobs/Zoo_Knobs_knobs_Gear_knobs/blocks/Knob_Showcase_Gear_Advanced/gear_05
oSCAssetsZooKnobsKnobsGearknobsZooKnobsknobsGearknobsBlocksKc8da OBJECT-TYPE
    SYNTAX      DisplayString
    MAX-ACCESS  read-write
    STATUS      current
    DESCRIPTION "Source: OPEN-AIR/OSC/Assets/Zoo/Knobs/knobs/Gear_knobs/Zoo_Knobs_knobs_Gear_knobs/blocks/Knob_Showcase_Gear_Advanced/gear_05"
    ::= { oSCAssetsZooKnobsKnobsGearknobsZooKnobsknobsGearknobsBlocksKfcba 29483 }

-- MQTT: OPEN-AIR/OSC/Assets/Zoo/Knobs/knobs/Gear_knobs/Zoo_Knobs_knobs_Gear_knobs/blocks/Knob_Showcase_Gear_Advanced/gear_10
oSCAssetsZooKnobsKnobsGearknobsZooKnobsknobsGearknobsBlocksKa1ab OBJECT-TYPE
    SYNTAX      DisplayString
    MAX-ACCESS  read-write
    STATUS      current
    DESCRIPTION "Source: OPEN-AIR/OSC/Assets/Zoo/Knobs/knobs/Gear_knobs/Zoo_Knobs_knobs_Gear_knobs/blocks/Knob_Showcase_Gear_Advanced/gear_10"
    ::= { oSCAssetsZooKnobsKnobsGearknobsZooKnobsknobsGearknobsBlocksKfcba 46821 }

-- MQTT: OPEN-AIR/OSC/Assets/Zoo/Knobs/knobs/Gear_knobs/Zoo_Knobs_knobs_Gear_knobs/blocks/Knob_Showcase_Gear_Advanced/gear_02
oSCAssetsZooKnobsKnobsGearknobsZooKnobsknobsGearknobsBlocksK56be OBJECT-TYPE
    SYNTAX      DisplayString
    MAX-ACCESS  read-write
    STATUS      current
    DESCRIPTION "Source: OPEN-AIR/OSC/Assets/Zoo/Knobs/knobs/Gear_knobs/Zoo_Knobs_knobs_Gear_knobs/blocks/Knob_Showcase_Gear_Advanced/gear_02"
    ::= { oSCAssetsZooKnobsKnobsGearknobsZooKnobsknobsGearknobsBlocksKfcba 59016 }

oSCAssetsZooKnobsKnobsKnobd9bb OBJECT IDENTIFIER ::= { oSCAssetsZooKnobsKnobs32a3 45475 }
oSCAssetsZooKnobsKnobsKnobZooKnobsknobsknob1bf68 OBJECT IDENTIFIER ::= { oSCAssetsZooKnobsKnobsKnobd9bb 17423 }
oSCAssetsZooKnobsKnobsKnobZooKnobsknobsknob1Blocks5564 OBJECT IDENTIFIER ::= { oSCAssetsZooKnobsKnobsKnobZooKnobsknobsknob1bf68 63491 }
oSCAssetsZooKnobsKnobsKnobZooKnobsknobsknob1BlocksKnobZooDri45fa OBJECT IDENTIFIER ::= { oSCAssetsZooKnobsKnobsKnobZooKnobsknobsknob1Blocks5564 22359 }
-- MQTT: OPEN-AIR/OSC/Assets/Zoo/Knobs/knobs/knob/Zoo_Knobs_knobs_knob_1/blocks/Knob_Zoo_Drive/knob_drv1
oSCAssetsZooKnobsKnobsKnobZooKnobsknobsknob1BlocksKnobZooDri3ae3 OBJECT-TYPE
    SYNTAX      DisplayString
    MAX-ACCESS  read-write
    STATUS      current
    DESCRIPTION "Source: OPEN-AIR/OSC/Assets/Zoo/Knobs/knobs/knob/Zoo_Knobs_knobs_knob_1/blocks/Knob_Zoo_Drive/knob_drv1"
    ::= { oSCAssetsZooKnobsKnobsKnobZooKnobsknobsknob1BlocksKnobZooDri45fa 46702 }

oSCAssetsZooButtonse722 OBJECT IDENTIFIER ::= { oSCAssetsZoofaa0 62234 }
oSCAssetsZooButtonsTrapezoid329d OBJECT IDENTIFIER ::= { oSCAssetsZooButtonse722 11316 }
oSCAssetsZooButtonsTrapezoidTrapezoidbutton1f79 OBJECT IDENTIFIER ::= { oSCAssetsZooButtonsTrapezoid329d 35866 }
oSCAssetsZooButtonsTrapezoidTrapezoidbuttonZoobuttonsTrapezo676e OBJECT IDENTIFIER ::= { oSCAssetsZooButtonsTrapezoidTrapezoidbutton1f79 59629 }
oSCAssetsZooButtonsTrapezoidTrapezoidbuttonZoobuttonsTrapezoc325 OBJECT IDENTIFIER ::= { oSCAssetsZooButtonsTrapezoidTrapezoidbuttonZoobuttonsTrapezo676e 64126 }
oSCAssetsZooButtonsTrapezoidTrapezoidbuttonZoobuttonsTrapezo9725 OBJECT IDENTIFIER ::= { oSCAssetsZooButtonsTrapezoidTrapezoidbuttonZoobuttonsTrapezoc325 35707 }
-- MQTT: OPEN-AIR/OSC/Assets/Zoo/buttons/Trapezoid/trapezoid_button/Zoo_buttons_Trapezoid_trapezoid_button/blocks/Trapezoid_Button_REC_Variations/rec_demo3
oSCAssetsZooButtonsTrapezoidTrapezoidbuttonZoobuttonsTrapezo50a4 OBJECT-TYPE
    SYNTAX      DisplayString
    MAX-ACCESS  read-write
    STATUS      current
    DESCRIPTION "Source: OPEN-AIR/OSC/Assets/Zoo/buttons/Trapezoid/trapezoid_button/Zoo_buttons_Trapezoid_trapezoid_button/blocks/Trapezoid_Button_REC_Variations/rec_demo3"
    ::= { oSCAssetsZooButtonsTrapezoidTrapezoidbuttonZoobuttonsTrapezo9725 50481 }

oSCAssetsZooButtonsTrapezoidTrapezoidbuttonZoobuttonsTrapezo347c OBJECT IDENTIFIER ::= { oSCAssetsZooButtonsTrapezoidTrapezoidbuttonZoobuttonsTrapezoc325 57796 }
-- MQTT: OPEN-AIR/OSC/Assets/Zoo/buttons/Trapezoid/trapezoid_button/Zoo_buttons_Trapezoid_trapezoid_button/blocks/Trapezoid_Button_Petting_Zoo/mode_cyan_wide
oSCAssetsZooButtonsTrapezoidTrapezoidbuttonZoobuttonsTrapezoe180 OBJECT-TYPE
    SYNTAX      DisplayString
    MAX-ACCESS  read-write
    STATUS      current
    DESCRIPTION "Source: OPEN-AIR/OSC/Assets/Zoo/buttons/Trapezoid/trapezoid_button/Zoo_buttons_Trapezoid_trapezoid_button/blocks/Trapezoid_Button_Petting_Zoo/mode_cyan_wide"
    ::= { oSCAssetsZooButtonsTrapezoidTrapezoidbuttonZoobuttonsTrapezo347c 3180 }

assets79d1 OBJECT IDENTIFIER ::= { v1 32142 }
assetsSpectrum9965 OBJECT IDENTIFIER ::= { assets79d1 0 }
assetsSpectrumInstrument5d2b OBJECT IDENTIFIER ::= { assetsSpectrum9965 3 }
assetsSpectrumInstrumentFrequencyf29b OBJECT IDENTIFIER ::= { assetsSpectrumInstrument5d2b 1 }
assetsSpectrumInstrumentFrequencySpectrumInstrumentfrequency1a26 OBJECT IDENTIFIER ::= { assetsSpectrumInstrumentFrequencyf29b 33369 }
assetsSpectrumInstrumentFrequencySpectrumInstrumentfrequency4fa6 OBJECT IDENTIFIER ::= { assetsSpectrumInstrumentFrequencySpectrumInstrumentfrequency1a26 54840 }
assetsSpectrumInstrumentFrequencySpectrumInstrumentfrequency5ff2 OBJECT IDENTIFIER ::= { assetsSpectrumInstrumentFrequencySpectrumInstrumentfrequency4fa6 36210 }
-- MQTT: OPEN-AIR/Assets/Spectrum/Instrument/frequency/Spectrum_Instrument_frequency/blocks/Frequency/center_freq_MHz
assetsSpectrumInstrumentFrequencySpectrumInstrumentfrequencyf074 OBJECT-TYPE
    SYNTAX      DisplayString
    MAX-ACCESS  read-write
    STATUS      current
    DESCRIPTION "Source: OPEN-AIR/Assets/Spectrum/Instrument/frequency/Spectrum_Instrument_frequency/blocks/Frequency/center_freq_MHz"
    ::= { assetsSpectrumInstrumentFrequencySpectrumInstrumentfrequency5ff2 31728 }

-- MQTT: OPEN-AIR/Assets/Spectrum/Instrument/frequency/Spectrum_Instrument_frequency/blocks/Frequency/span_freq_MHz
assetsSpectrumInstrumentFrequencySpectrumInstrumentfrequencya7ab OBJECT-TYPE
    SYNTAX      DisplayString
    MAX-ACCESS  read-write
    STATUS      current
    DESCRIPTION "Source: OPEN-AIR/Assets/Spectrum/Instrument/frequency/Spectrum_Instrument_frequency/blocks/Frequency/span_freq_MHz"
    ::= { assetsSpectrumInstrumentFrequencySpectrumInstrumentfrequency5ff2 48513 }

assetsSpectrumInstrumentFrequencySpectrumInstrumentfrequency5766 OBJECT IDENTIFIER ::= { assetsSpectrumInstrumentFrequencySpectrumInstrumentfrequency4fa6 36959 }
-- MQTT: OPEN-AIR/Assets/Spectrum/Instrument/frequency/Spectrum_Instrument_frequency/blocks/Quick Span/Span
assetsSpectrumInstrumentFrequencySpectrumInstrumentfrequencyc087 OBJECT-TYPE
    SYNTAX      DisplayString
    MAX-ACCESS  read-write
    STATUS      current
    DESCRIPTION "Source: OPEN-AIR/Assets/Spectrum/Instrument/frequency/Spectrum_Instrument_frequency/blocks/Quick Span/Span"
    ::= { assetsSpectrumInstrumentFrequencySpectrumInstrumentfrequency5766 64492 }

assetsSpectrumInstrumentFrequencySpectrumInstrumentfrequencyc7a1 OBJECT IDENTIFIER ::= { assetsSpectrumInstrumentFrequencySpectrumInstrumentfrequency4fa6 53393 }
-- MQTT: OPEN-AIR/Assets/Spectrum/Instrument/frequency/Spectrum_Instrument_frequency/blocks/Start Stop/start_freq_MHz
assetsSpectrumInstrumentFrequencySpectrumInstrumentfrequency6298 OBJECT-TYPE
    SYNTAX      DisplayString
    MAX-ACCESS  read-write
    STATUS      current
    DESCRIPTION "Source: OPEN-AIR/Assets/Spectrum/Instrument/frequency/Spectrum_Instrument_frequency/blocks/Start Stop/start_freq_MHz"
    ::= { assetsSpectrumInstrumentFrequencySpectrumInstrumentfrequencyc7a1 2369 }

-- MQTT: OPEN-AIR/Assets/Spectrum/Instrument/frequency/Spectrum_Instrument_frequency/blocks/Start Stop/stop_freq_MHz
assetsSpectrumInstrumentFrequencySpectrumInstrumentfrequency7735 OBJECT-TYPE
    SYNTAX      DisplayString
    MAX-ACCESS  read-write
    STATUS      current
    DESCRIPTION "Source: OPEN-AIR/Assets/Spectrum/Instrument/frequency/Spectrum_Instrument_frequency/blocks/Start Stop/stop_freq_MHz"
    ::= { assetsSpectrumInstrumentFrequencySpectrumInstrumentfrequencyc7a1 38481 }

assetsSpectrumInstrumentBandwidth5eed OBJECT IDENTIFIER ::= { assetsSpectrumInstrument5d2b 2 }
assetsSpectrumInstrumentBandwidthSpectrumInstrumentbandwidth88b1 OBJECT IDENTIFIER ::= { assetsSpectrumInstrumentBandwidth5eed 5104 }
assetsSpectrumInstrumentBandwidthSpectrumInstrumentbandwidth3908 OBJECT IDENTIFIER ::= { assetsSpectrumInstrumentBandwidthSpectrumInstrumentbandwidth88b1 16720 }
assetsSpectrumInstrumentBandwidthSpectrumInstrumentbandwidth9ba3 OBJECT IDENTIFIER ::= { assetsSpectrumInstrumentBandwidthSpectrumInstrumentbandwidth3908 1893 }
assetsSpectrumInstrumentBandwidthSpectrumInstrumentbandwidthfc8a OBJECT IDENTIFIER ::= { assetsSpectrumInstrumentBandwidthSpectrumInstrumentbandwidth9ba3 34210 }
-- MQTT: OPEN-AIR/Assets/Spectrum/Instrument/bandwidth/Spectrum_Instrument_bandwidth/blocks/Resolution Bandwidth/RBW/dial_config
assetsSpectrumInstrumentBandwidthSpectrumInstrumentbandwidthb398 OBJECT-TYPE
    SYNTAX      DisplayString
    MAX-ACCESS  read-write
    STATUS      current
    DESCRIPTION "Source: OPEN-AIR/Assets/Spectrum/Instrument/bandwidth/Spectrum_Instrument_bandwidth/blocks/Resolution Bandwidth/RBW/dial_config"
    ::= { assetsSpectrumInstrumentBandwidthSpectrumInstrumentbandwidthfc8a 25960 }

-- MQTT: OPEN-AIR/Assets/Spectrum/Instrument/bandwidth/Spectrum_Instrument_bandwidth/blocks/Resolution Bandwidth/RBW/fader_config
assetsSpectrumInstrumentBandwidthSpectrumInstrumentbandwidth4905 OBJECT-TYPE
    SYNTAX      DisplayString
    MAX-ACCESS  read-write
    STATUS      current
    DESCRIPTION "Source: OPEN-AIR/Assets/Spectrum/Instrument/bandwidth/Spectrum_Instrument_bandwidth/blocks/Resolution Bandwidth/RBW/fader_config"
    ::= { assetsSpectrumInstrumentBandwidthSpectrumInstrumentbandwidthfc8a 31626 }

assetsSpectrumInstrumentBandwidthSpectrumInstrumentbandwidth1a75 OBJECT IDENTIFIER ::= { assetsSpectrumInstrumentBandwidthSpectrumInstrumentbandwidth3908 43407 }
-- MQTT: OPEN-AIR/Assets/Spectrum/Instrument/bandwidth/Spectrum_Instrument_bandwidth/blocks/Sweep Time/sweep_time_setting
assetsSpectrumInstrumentBandwidthSpectrumInstrumentbandwidthcee7 OBJECT-TYPE
    SYNTAX      DisplayString
    MAX-ACCESS  read-write
    STATUS      current
    DESCRIPTION "Source: OPEN-AIR/Assets/Spectrum/Instrument/bandwidth/Spectrum_Instrument_bandwidth/blocks/Sweep Time/sweep_time_setting"
    ::= { assetsSpectrumInstrumentBandwidthSpectrumInstrumentbandwidth1a75 22849 }

assetsSpectrumInstrumentBandwidthSpectrumInstrumentbandwidthe565 OBJECT IDENTIFIER ::= { assetsSpectrumInstrumentBandwidthSpectrumInstrumentbandwidth3908 45850 }
-- MQTT: OPEN-AIR/Assets/Spectrum/Instrument/bandwidth/Spectrum_Instrument_bandwidth/blocks/Video Bandwidth/Video Band Width 
assetsSpectrumInstrumentBandwidthSpectrumInstrumentbandwidth4021 OBJECT-TYPE
    SYNTAX      DisplayString
    MAX-ACCESS  read-write
    STATUS      current
    DESCRIPTION "Source: OPEN-AIR/Assets/Spectrum/Instrument/bandwidth/Spectrum_Instrument_bandwidth/blocks/Video Bandwidth/Video Band Width "
    ::= { assetsSpectrumInstrumentBandwidthSpectrumInstrumentbandwidthe565 504 }

assetsSpectrumInstrumentBandwidthSpectrumInstrumentbandwidth4e7c OBJECT IDENTIFIER ::= { assetsSpectrumInstrumentBandwidthSpectrumInstrumentbandwidthe565 18590 }
-- MQTT: OPEN-AIR/Assets/Spectrum/Instrument/bandwidth/Spectrum_Instrument_bandwidth/blocks/Video Bandwidth/vbw_MHz/fader_config
assetsSpectrumInstrumentBandwidthSpectrumInstrumentbandwidthf1b8 OBJECT-TYPE
    SYNTAX      DisplayString
    MAX-ACCESS  read-write
    STATUS      current
    DESCRIPTION "Source: OPEN-AIR/Assets/Spectrum/Instrument/bandwidth/Spectrum_Instrument_bandwidth/blocks/Video Bandwidth/vbw_MHz/fader_config"
    ::= { assetsSpectrumInstrumentBandwidthSpectrumInstrumentbandwidth4e7c 139 }

-- MQTT: OPEN-AIR/Assets/Spectrum/Instrument/bandwidth/Spectrum_Instrument_bandwidth/blocks/Video Bandwidth/vbw_MHz/dial_config
assetsSpectrumInstrumentBandwidthSpectrumInstrumentbandwidthb346 OBJECT-TYPE
    SYNTAX      DisplayString
    MAX-ACCESS  read-write
    STATUS      current
    DESCRIPTION "Source: OPEN-AIR/Assets/Spectrum/Instrument/bandwidth/Spectrum_Instrument_bandwidth/blocks/Video Bandwidth/vbw_MHz/dial_config"
    ::= { assetsSpectrumInstrumentBandwidthSpectrumInstrumentbandwidth4e7c 27487 }

-- MQTT: OPEN-AIR/Assets/Spectrum/Instrument/bandwidth/Spectrum_Instrument_bandwidth/blocks/Video Bandwidth/VBW_Automatic
assetsSpectrumInstrumentBandwidthSpectrumInstrumentbandwidthdc93 OBJECT-TYPE
    SYNTAX      DisplayString
    MAX-ACCESS  read-write
    STATUS      current
    DESCRIPTION "Source: OPEN-AIR/Assets/Spectrum/Instrument/bandwidth/Spectrum_Instrument_bandwidth/blocks/Video Bandwidth/VBW_Automatic"
    ::= { assetsSpectrumInstrumentBandwidthSpectrumInstrumentbandwidthe565 26832 }

assetsSpectrumInstrumentAmplitudebf49 OBJECT IDENTIFIER ::= { assetsSpectrumInstrument5d2b 3 }
assetsSpectrumInstrumentAmplitudeSpectrumInstrumentamplitude398c OBJECT IDENTIFIER ::= { assetsSpectrumInstrumentAmplitudebf49 38833 }
assetsSpectrumInstrumentAmplitudeSpectrumInstrumentamplitudea4e2 OBJECT IDENTIFIER ::= { assetsSpectrumInstrumentAmplitudeSpectrumInstrumentamplitude398c 10887 }
assetsSpectrumInstrumentAmplitudeSpectrumInstrumentamplitude3b4d OBJECT IDENTIFIER ::= { assetsSpectrumInstrumentAmplitudeSpectrumInstrumentamplitudea4e2 10366 }
-- MQTT: OPEN-AIR/Assets/Spectrum/Instrument/amplitude/Spectrum_Instrument_amplitude/blocks/Pre Amp/preamp_on
assetsSpectrumInstrumentAmplitudeSpectrumInstrumentamplitudeb56b OBJECT-TYPE
    SYNTAX      DisplayString
    MAX-ACCESS  read-write
    STATUS      current
    DESCRIPTION "Source: OPEN-AIR/Assets/Spectrum/Instrument/amplitude/Spectrum_Instrument_amplitude/blocks/Pre Amp/preamp_on"
    ::= { assetsSpectrumInstrumentAmplitudeSpectrumInstrumentamplitude3b4d 10352 }

-- MQTT: OPEN-AIR/Assets/Spectrum/Instrument/amplitude/Spectrum_Instrument_amplitude/blocks/Pre Amp/high_sensitivity_on
assetsSpectrumInstrumentAmplitudeSpectrumInstrumentamplitude12e7 OBJECT-TYPE
    SYNTAX      DisplayString
    MAX-ACCESS  read-write
    STATUS      current
    DESCRIPTION "Source: OPEN-AIR/Assets/Spectrum/Instrument/amplitude/Spectrum_Instrument_amplitude/blocks/Pre Amp/high_sensitivity_on"
    ::= { assetsSpectrumInstrumentAmplitudeSpectrumInstrumentamplitude3b4d 48061 }

assetsSpectrumInstrumentAmplitudeSpectrumInstrumentamplitude7fff OBJECT IDENTIFIER ::= { assetsSpectrumInstrumentAmplitudeSpectrumInstrumentamplitudea4e2 33806 }
assetsSpectrumInstrumentAmplitudeSpectrumInstrumentamplitudeed73 OBJECT IDENTIFIER ::= { assetsSpectrumInstrumentAmplitudeSpectrumInstrumentamplitude7fff 13085 }
-- MQTT: OPEN-AIR/Assets/Spectrum/Instrument/amplitude/Spectrum_Instrument_amplitude/blocks/Attenuation/power_attenuation_dB/fader_config
assetsSpectrumInstrumentAmplitudeSpectrumInstrumentamplitudef526 OBJECT-TYPE
    SYNTAX      DisplayString
    MAX-ACCESS  read-write
    STATUS      current
    DESCRIPTION "Source: OPEN-AIR/Assets/Spectrum/Instrument/amplitude/Spectrum_Instrument_amplitude/blocks/Attenuation/power_attenuation_dB/fader_config"
    ::= { assetsSpectrumInstrumentAmplitudeSpectrumInstrumentamplitudeed73 22020 }

-- MQTT: OPEN-AIR/Assets/Spectrum/Instrument/amplitude/Spectrum_Instrument_amplitude/blocks/Attenuation/power_attenuation_dB/dial_config
assetsSpectrumInstrumentAmplitudeSpectrumInstrumentamplitudef636 OBJECT-TYPE
    SYNTAX      DisplayString
    MAX-ACCESS  read-write
    STATUS      current
    DESCRIPTION "Source: OPEN-AIR/Assets/Spectrum/Instrument/amplitude/Spectrum_Instrument_amplitude/blocks/Attenuation/power_attenuation_dB/dial_config"
    ::= { assetsSpectrumInstrumentAmplitudeSpectrumInstrumentamplitudeed73 61913 }

-- MQTT: OPEN-AIR/Assets/Spectrum/Instrument/amplitude/Spectrum_Instrument_amplitude/blocks/Attenuation/POWER_ATTENUATION
assetsSpectrumInstrumentAmplitudeSpectrumInstrumentamplitude5e94 OBJECT-TYPE
    SYNTAX      DisplayString
    MAX-ACCESS  read-write
    STATUS      current
    DESCRIPTION "Source: OPEN-AIR/Assets/Spectrum/Instrument/amplitude/Spectrum_Instrument_amplitude/blocks/Attenuation/POWER_ATTENUATION"
    ::= { assetsSpectrumInstrumentAmplitudeSpectrumInstrumentamplitude7fff 18603 }

assetsSpectrumInstrumentAmplitudeSpectrumInstrumentamplitude6721 OBJECT IDENTIFIER ::= { assetsSpectrumInstrumentAmplitudeSpectrumInstrumentamplitudea4e2 45561 }
assetsSpectrumInstrumentAmplitudeSpectrumInstrumentamplitude86bf OBJECT IDENTIFIER ::= { assetsSpectrumInstrumentAmplitudeSpectrumInstrumentamplitude6721 5605 }
-- MQTT: OPEN-AIR/Assets/Spectrum/Instrument/amplitude/Spectrum_Instrument_amplitude/blocks/Reference Level/ref_level_dBm/fader_config
assetsSpectrumInstrumentAmplitudeSpectrumInstrumentamplitude5d72 OBJECT-TYPE
    SYNTAX      DisplayString
    MAX-ACCESS  read-write
    STATUS      current
    DESCRIPTION "Source: OPEN-AIR/Assets/Spectrum/Instrument/amplitude/Spectrum_Instrument_amplitude/blocks/Reference Level/ref_level_dBm/fader_config"
    ::= { assetsSpectrumInstrumentAmplitudeSpectrumInstrumentamplitude86bf 40042 }

-- MQTT: OPEN-AIR/Assets/Spectrum/Instrument/amplitude/Spectrum_Instrument_amplitude/blocks/Reference Level/ref_level_dBm/dial_config
assetsSpectrumInstrumentAmplitudeSpectrumInstrumentamplitudec523 OBJECT-TYPE
    SYNTAX      DisplayString
    MAX-ACCESS  read-write
    STATUS      current
    DESCRIPTION "Source: OPEN-AIR/Assets/Spectrum/Instrument/amplitude/Spectrum_Instrument_amplitude/blocks/Reference Level/ref_level_dBm/dial_config"
    ::= { assetsSpectrumInstrumentAmplitudeSpectrumInstrumentamplitude86bf 51828 }

assetsSpectrumInstrumentMarkers4ec1 OBJECT IDENTIFIER ::= { assetsSpectrumInstrument5d2b 4 }
assetsSpectrumInstrumentMarkersSpectrumInstrumentmarkers5808 OBJECT IDENTIFIER ::= { assetsSpectrumInstrumentMarkers4ec1 427 }
assetsSpectrumInstrumentMarkersSpectrumInstrumentmarkersBloc6b8f OBJECT IDENTIFIER ::= { assetsSpectrumInstrumentMarkersSpectrumInstrumentmarkers5808 39533 }
assetsSpectrumInstrumentMarkersSpectrumInstrumentmarkersBlocbbe1 OBJECT IDENTIFIER ::= { assetsSpectrumInstrumentMarkersSpectrumInstrumentmarkersBloc6b8f 5250 }
-- MQTT: OPEN-AIR/Assets/Spectrum/Instrument/markers/Spectrum_Instrument_markers/blocks/Marker 3/Active
assetsSpectrumInstrumentMarkersSpectrumInstrumentmarkersBloca17d OBJECT-TYPE
    SYNTAX      DisplayString
    MAX-ACCESS  read-write
    STATUS      current
    DESCRIPTION "Source: OPEN-AIR/Assets/Spectrum/Instrument/markers/Spectrum_Instrument_markers/blocks/Marker 3/Active"
    ::= { assetsSpectrumInstrumentMarkersSpectrumInstrumentmarkersBlocbbe1 16776 }

assetsSpectrumInstrumentMarkersSpectrumInstrumentmarkersBloce5b0 OBJECT IDENTIFIER ::= { assetsSpectrumInstrumentMarkersSpectrumInstrumentmarkersBloc6b8f 30126 }
-- MQTT: OPEN-AIR/Assets/Spectrum/Instrument/markers/Spectrum_Instrument_markers/blocks/Marker 1/X_MHz
assetsSpectrumInstrumentMarkersSpectrumInstrumentmarkersBloce070 OBJECT-TYPE
    SYNTAX      DisplayString
    MAX-ACCESS  read-write
    STATUS      current
    DESCRIPTION "Source: OPEN-AIR/Assets/Spectrum/Instrument/markers/Spectrum_Instrument_markers/blocks/Marker 1/X_MHz"
    ::= { assetsSpectrumInstrumentMarkersSpectrumInstrumentmarkersBloce5b0 49332 }

assetsSpectrumInstrumentMarkersSpectrumInstrumentmarkersBloc95da OBJECT IDENTIFIER ::= { assetsSpectrumInstrumentMarkersSpectrumInstrumentmarkersBloc6b8f 33057 }
-- MQTT: OPEN-AIR/Assets/Spectrum/Instrument/markers/Spectrum_Instrument_markers/blocks/Marker 4/Y_dBm
assetsSpectrumInstrumentMarkersSpectrumInstrumentmarkersBlocf9c5 OBJECT-TYPE
    SYNTAX      DisplayString
    MAX-ACCESS  read-write
    STATUS      current
    DESCRIPTION "Source: OPEN-AIR/Assets/Spectrum/Instrument/markers/Spectrum_Instrument_markers/blocks/Marker 4/Y_dBm"
    ::= { assetsSpectrumInstrumentMarkersSpectrumInstrumentmarkersBloc95da 36961 }

assetsSpectrumInstrumentTracesf27c OBJECT IDENTIFIER ::= { assetsSpectrumInstrument5d2b 5 }
assetsSpectrumInstrumentTracesSpectrumInstrumenttraces8aee OBJECT IDENTIFIER ::= { assetsSpectrumInstrumentTracesf27c 21678 }
assetsSpectrumInstrumentTracesSpectrumInstrumenttracesBlocks4e3d OBJECT IDENTIFIER ::= { assetsSpectrumInstrumentTracesSpectrumInstrumenttraces8aee 28643 }
assetsSpectrumInstrumentTracesSpectrumInstrumenttracesBlocksdb61 OBJECT IDENTIFIER ::= { assetsSpectrumInstrumentTracesSpectrumInstrumenttracesBlocks4e3d 37350 }
-- MQTT: OPEN-AIR/Assets/Spectrum/Instrument/traces/Spectrum_Instrument_traces/blocks/Averaging/AVERAGING
assetsSpectrumInstrumentTracesSpectrumInstrumenttracesBlocksdc05 OBJECT-TYPE
    SYNTAX      DisplayString
    MAX-ACCESS  read-write
    STATUS      current
    DESCRIPTION "Source: OPEN-AIR/Assets/Spectrum/Instrument/traces/Spectrum_Instrument_traces/blocks/Averaging/AVERAGING"
    ::= { assetsSpectrumInstrumentTracesSpectrumInstrumenttracesBlocksdb61 64952 }

assetsSpectrumYAK2c1f OBJECT IDENTIFIER ::= { assetsSpectrum9965 10 }
assetsSpectrumYAKN9340B54e7 OBJECT IDENTIFIER ::= { assetsSpectrumYAK2c1f 1 }
assetsSpectrumYAKN9340BFrequencyf223 OBJECT IDENTIFIER ::= { assetsSpectrumYAKN9340B54e7 0 }
assetsSpectrumYAKN9340BFrequencySpectrumYAKN9340BFrequencyccbc OBJECT IDENTIFIER ::= { assetsSpectrumYAKN9340BFrequencyf223 534 }
assetsSpectrumYAKN9340BFrequencySpectrumYAKN9340BFrequencyBl7bdc OBJECT IDENTIFIER ::= { assetsSpectrumYAKN9340BFrequencySpectrumYAKN9340BFrequencyccbc 7812 }
assetsSpectrumYAKN9340BFrequencySpectrumYAKN9340BFrequencyBle833 OBJECT IDENTIFIER ::= { assetsSpectrumYAKN9340BFrequencySpectrumYAKN9340BFrequencyBl7bdc 62694 }
assetsSpectrumYAKN9340BFrequencySpectrumYAKN9340BFrequencyBleb1c OBJECT IDENTIFIER ::= { assetsSpectrumYAKN9340BFrequencySpectrumYAKN9340BFrequencyBle833 9333 }
assetsSpectrumYAKN9340BFrequencySpectrumYAKN9340BFrequencyBl89e4 OBJECT IDENTIFIER ::= { assetsSpectrumYAKN9340BFrequencySpectrumYAKN9340BFrequencyBleb1c 4442 }
-- MQTT: OPEN-AIR/Assets/Spectrum/YAK/N9340B/Frequency/Spectrum_YAK_N9340B_Frequency/blocks/RIG_Settings/freq_start_stop/Input/stop_freq
assetsSpectrumYAKN9340BFrequencySpectrumYAKN9340BFrequencyBl95e3 OBJECT-TYPE
    SYNTAX      DisplayString
    MAX-ACCESS  read-write
    STATUS      current
    DESCRIPTION "Source: OPEN-AIR/Assets/Spectrum/YAK/N9340B/Frequency/Spectrum_YAK_N9340B_Frequency/blocks/RIG_Settings/freq_start_stop/Input/stop_freq"
    ::= { assetsSpectrumYAKN9340BFrequencySpectrumYAKN9340BFrequencyBl89e4 14118 }

-- MQTT: OPEN-AIR/Assets/Spectrum/YAK/N9340B/Frequency/Spectrum_YAK_N9340B_Frequency/blocks/RIG_Settings/freq_start_stop/Input/start_freq
assetsSpectrumYAKN9340BFrequencySpectrumYAKN9340BFrequencyBl8cf7 OBJECT-TYPE
    SYNTAX      DisplayString
    MAX-ACCESS  read-write
    STATUS      current
    DESCRIPTION "Source: OPEN-AIR/Assets/Spectrum/YAK/N9340B/Frequency/Spectrum_YAK_N9340B_Frequency/blocks/RIG_Settings/freq_start_stop/Input/start_freq"
    ::= { assetsSpectrumYAKN9340BFrequencySpectrumYAKN9340BFrequencyBl89e4 64412 }

assetsSpectrumYAKN9340BFrequencySpectrumYAKN9340BFrequencyBl1ed0 OBJECT IDENTIFIER ::= { assetsSpectrumYAKN9340BFrequencySpectrumYAKN9340BFrequencyBle833 51493 }
assetsSpectrumYAKN9340BFrequencySpectrumYAKN9340BFrequencyBldaba OBJECT IDENTIFIER ::= { assetsSpectrumYAKN9340BFrequencySpectrumYAKN9340BFrequencyBl1ed0 64070 }
-- MQTT: OPEN-AIR/Assets/Spectrum/YAK/N9340B/Frequency/Spectrum_YAK_N9340B_Frequency/blocks/RIG_Settings/Stop_Freq_MHz/Input/hz_value
assetsSpectrumYAKN9340BFrequencySpectrumYAKN9340BFrequencyBl2259 OBJECT-TYPE
    SYNTAX      DisplayString
    MAX-ACCESS  read-write
    STATUS      current
    DESCRIPTION "Source: OPEN-AIR/Assets/Spectrum/YAK/N9340B/Frequency/Spectrum_YAK_N9340B_Frequency/blocks/RIG_Settings/Stop_Freq_MHz/Input/hz_value"
    ::= { assetsSpectrumYAKN9340BFrequencySpectrumYAKN9340BFrequencyBldaba 9492 }

assetsScan8571 OBJECT IDENTIFIER ::= { assets79d1 1 }
assetsScanScan39a8 OBJECT IDENTIFIER ::= { assetsScan8571 27445 }
assetsScanScanBlocks8eaa OBJECT IDENTIFIER ::= { assetsScanScan39a8 46272 }
assetsScanScanBlocksMultidatasetgraphc492 OBJECT IDENTIFIER ::= { assetsScanScanBlocks8eaa 19071 }
assetsScanScanBlocksMultidatasetgraphOaDataRunningFilesfdbd OBJECT IDENTIFIER ::= { assetsScanScanBlocksMultidatasetgraphc492 9507 }
-- MQTT: OPEN-AIR/Assets/scan/scan/blocks/multi_dataset_graph/oaDataRunningFiles/MARKERS
assetsScanScanBlocksMultidatasetgraphOaDataRunningFilesMARKE651d OBJECT-TYPE
    SYNTAX      DisplayString
    MAX-ACCESS  read-write
    STATUS      current
    DESCRIPTION "Source: OPEN-AIR/Assets/scan/scan/blocks/multi_dataset_graph/oaDataRunningFiles/MARKERS"
    ::= { assetsScanScanBlocksMultidatasetgraphOaDataRunningFilesfdbd 18452 }

-- MQTT: OPEN-AIR/Assets/scan/scan/blocks/multi_dataset_graph/oaDataRunningFiles/ref_linear
assetsScanScanBlocksMultidatasetgraphOaDataRunningFilesRefli8ee1 OBJECT-TYPE
    SYNTAX      DisplayString
    MAX-ACCESS  read-write
    STATUS      current
    DESCRIPTION "Source: OPEN-AIR/Assets/scan/scan/blocks/multi_dataset_graph/oaDataRunningFiles/ref_linear"
    ::= { assetsScanScanBlocksMultidatasetgraphOaDataRunningFilesfdbd 30162 }

assetsScanScanBlocksMultidatasetgraphSettings5e4f OBJECT IDENTIFIER ::= { assetsScanScanBlocksMultidatasetgraphc492 53222 }
-- MQTT: OPEN-AIR/Assets/scan/scan/blocks/multi_dataset_graph/settings/x_label
assetsScanScanBlocksMultidatasetgraphSettingsXlabela969 OBJECT-TYPE
    SYNTAX      DisplayString
    MAX-ACCESS  read-write
    STATUS      current
    DESCRIPTION "Source: OPEN-AIR/Assets/scan/scan/blocks/multi_dataset_graph/settings/x_label"
    ::= { assetsScanScanBlocksMultidatasetgraphSettings5e4f 9887 }

-- MQTT: OPEN-AIR/Assets/scan/scan/blocks/multi_dataset_graph/settings/ylim
assetsScanScanBlocksMultidatasetgraphSettingsYlim8331 OBJECT-TYPE
    SYNTAX      DisplayString
    MAX-ACCESS  read-write
    STATUS      current
    DESCRIPTION "Source: OPEN-AIR/Assets/scan/scan/blocks/multi_dataset_graph/settings/ylim"
    ::= { assetsScanScanBlocksMultidatasetgraphSettings5e4f 10649 }

-- MQTT: OPEN-AIR/Assets/scan/scan/blocks/multi_dataset_graph/settings/y_label
assetsScanScanBlocksMultidatasetgraphSettingsYlabelf1e2 OBJECT-TYPE
    SYNTAX      DisplayString
    MAX-ACCESS  read-write
    STATUS      current
    DESCRIPTION "Source: OPEN-AIR/Assets/scan/scan/blocks/multi_dataset_graph/settings/y_label"
    ::= { assetsScanScanBlocksMultidatasetgraphSettings5e4f 11563 }

-- MQTT: OPEN-AIR/Assets/scan/scan/blocks/multi_dataset_graph/settings/xlim
assetsScanScanBlocksMultidatasetgraphSettingsXlim3b8d OBJECT-TYPE
    SYNTAX      DisplayString
    MAX-ACCESS  read-write
    STATUS      current
    DESCRIPTION "Source: OPEN-AIR/Assets/scan/scan/blocks/multi_dataset_graph/settings/xlim"
    ::= { assetsScanScanBlocksMultidatasetgraphSettings5e4f 20220 }

-- MQTT: OPEN-AIR/Assets/scan/scan/blocks/multi_dataset_graph/settings/title
assetsScanScanBlocksMultidatasetgraphSettingsTitlea421 OBJECT-TYPE
    SYNTAX      DisplayString
    MAX-ACCESS  read-write
    STATUS      current
    DESCRIPTION "Source: OPEN-AIR/Assets/scan/scan/blocks/multi_dataset_graph/settings/title"
    ::= { assetsScanScanBlocksMultidatasetgraphSettings5e4f 21874 }

-- MQTT: OPEN-AIR/Assets/scan/scan/blocks/multi_dataset_graph/settings/show_grid
assetsScanScanBlocksMultidatasetgraphSettingsShowgrid97d7 OBJECT-TYPE
    SYNTAX      DisplayString
    MAX-ACCESS  read-write
    STATUS      current
    DESCRIPTION "Source: OPEN-AIR/Assets/scan/scan/blocks/multi_dataset_graph/settings/show_grid"
    ::= { assetsScanScanBlocksMultidatasetgraphSettings5e4f 55413 }

assetsMonitorse005 OBJECT IDENTIFIER ::= { assets79d1 2 }
assetsMonitorsGraphs5c0a OBJECT IDENTIFIER ::= { assetsMonitorse005 00 }
assetsMonitorsGraphsMonitors7920 OBJECT IDENTIFIER ::= { assetsMonitorsGraphs5c0a 33517 }
assetsMonitorsGraphsMonitorsSettings2d1a OBJECT IDENTIFIER ::= { assetsMonitorsGraphsMonitors7920 43006 }
-- MQTT: OPEN-AIR/Assets/monitors/Graphs/monitors/settings/show_grid
assetsMonitorsGraphsMonitorsSettingsShowgrid9a6a OBJECT-TYPE
    SYNTAX      DisplayString
    MAX-ACCESS  read-write
    STATUS      current
    DESCRIPTION "Source: OPEN-AIR/Assets/monitors/Graphs/monitors/settings/show_grid"
    ::= { assetsMonitorsGraphsMonitorsSettings2d1a 8149 }

-- MQTT: OPEN-AIR/Assets/monitors/Graphs/monitors/settings/y_label
assetsMonitorsGraphsMonitorsSettingsYlabelc296 OBJECT-TYPE
    SYNTAX      DisplayString
    MAX-ACCESS  read-write
    STATUS      current
    DESCRIPTION "Source: OPEN-AIR/Assets/monitors/Graphs/monitors/settings/y_label"
    ::= { assetsMonitorsGraphsMonitorsSettings2d1a 20686 }

-- MQTT: OPEN-AIR/Assets/monitors/Graphs/monitors/settings/x_label
assetsMonitorsGraphsMonitorsSettingsXlabel64e1 OBJECT-TYPE
    SYNTAX      DisplayString
    MAX-ACCESS  read-write
    STATUS      current
    DESCRIPTION "Source: OPEN-AIR/Assets/monitors/Graphs/monitors/settings/x_label"
    ::= { assetsMonitorsGraphsMonitorsSettings2d1a 23418 }

-- MQTT: OPEN-AIR/Assets/monitors/Graphs/monitors/settings/title
assetsMonitorsGraphsMonitorsSettingsTitledadf OBJECT-TYPE
    SYNTAX      DisplayString
    MAX-ACCESS  read-write
    STATUS      current
    DESCRIPTION "Source: OPEN-AIR/Assets/monitors/Graphs/monitors/settings/title"
    ::= { assetsMonitorsGraphsMonitorsSettings2d1a 43083 }

-- MQTT: OPEN-AIR/Assets/monitors/Graphs/monitors/settings/ylim
assetsMonitorsGraphsMonitorsSettingsYlimccb0 OBJECT-TYPE
    SYNTAX      DisplayString
    MAX-ACCESS  read-write
    STATUS      current
    DESCRIPTION "Source: OPEN-AIR/Assets/monitors/Graphs/monitors/settings/ylim"
    ::= { assetsMonitorsGraphsMonitorsSettings2d1a 44436 }

-- MQTT: OPEN-AIR/Assets/monitors/Graphs/monitors/settings/xlim
assetsMonitorsGraphsMonitorsSettingsXlim740c OBJECT-TYPE
    SYNTAX      DisplayString
    MAX-ACCESS  read-write
    STATUS      current
    DESCRIPTION "Source: OPEN-AIR/Assets/monitors/Graphs/monitors/settings/xlim"
    ::= { assetsMonitorsGraphsMonitorsSettings2d1a 51953 }

assetsMonitorsGraphsMonitorsOaDataRunningFilesf000 OBJECT IDENTIFIER ::= { assetsMonitorsGraphsMonitors7920 57987 }
-- MQTT: OPEN-AIR/Assets/monitors/Graphs/monitors/oaDataRunningFiles/MARKERS
assetsMonitorsGraphsMonitorsOaDataRunningFilesMARKERS982e OBJECT-TYPE
    SYNTAX      DisplayString
    MAX-ACCESS  read-write
    STATUS      current
    DESCRIPTION "Source: OPEN-AIR/Assets/monitors/Graphs/monitors/oaDataRunningFiles/MARKERS"
    ::= { assetsMonitorsGraphsMonitorsOaDataRunningFilesf000 51847 }

assetsZoo5f4e OBJECT IDENTIFIER ::= { assets79d1 9 }
assetsZooFadersee8d OBJECT IDENTIFIER ::= { assetsZoo5f4e 0 }
assetsZooFadersLTP268f OBJECT IDENTIFIER ::= { assetsZooFadersee8d 0 }
assetsZooFadersLTPZooFadersLTP9bbe OBJECT IDENTIFIER ::= { assetsZooFadersLTP268f 48599 }
assetsZooFadersLTPZooFadersLTPBlocksd630 OBJECT IDENTIFIER ::= { assetsZooFadersLTPZooFadersLTP9bbe 20320 }
assetsZooFadersLTPZooFadersLTPBlocksLTPFreestyleConsolec0ad OBJECT IDENTIFIER ::= { assetsZooFadersLTPZooFadersLTPBlocksd630 12292 }
assetsZooFadersLTPZooFadersLTPBlocksLTPFreestyleConsoleCH6dade OBJECT IDENTIFIER ::= { assetsZooFadersLTPZooFadersLTPBlocksLTPFreestyleConsolec0ad 5096 }
-- MQTT: OPEN-AIR/Assets/Zoo/Faders/LTP/Zoo_Faders_LTP/blocks/LTP_Freestyle_Console/CH6/rotation
assetsZooFadersLTPZooFadersLTPBlocksLTPFreestyleConsoleCH6Rocc9c OBJECT-TYPE
    SYNTAX      DisplayString
    MAX-ACCESS  read-write
    STATUS      current
    DESCRIPTION "Source: OPEN-AIR/Assets/Zoo/Faders/LTP/Zoo_Faders_LTP/blocks/LTP_Freestyle_Console/CH6/rotation"
    ::= { assetsZooFadersLTPZooFadersLTPBlocksLTPFreestyleConsoleCH6dade 19502 }

assetsZooFadersLTPZooFadersLTPBlocksLTPFreestyleConsoleCH543d7 OBJECT IDENTIFIER ::= { assetsZooFadersLTPZooFadersLTPBlocksLTPFreestyleConsolec0ad 16978 }
-- MQTT: OPEN-AIR/Assets/Zoo/Faders/LTP/Zoo_Faders_LTP/blocks/LTP_Freestyle_Console/CH5/rotation
assetsZooFadersLTPZooFadersLTPBlocksLTPFreestyleConsoleCH5Ro27ab OBJECT-TYPE
    SYNTAX      DisplayString
    MAX-ACCESS  read-write
    STATUS      current
    DESCRIPTION "Source: OPEN-AIR/Assets/Zoo/Faders/LTP/Zoo_Faders_LTP/blocks/LTP_Freestyle_Console/CH5/rotation"
    ::= { assetsZooFadersLTPZooFadersLTPBlocksLTPFreestyleConsoleCH543d7 63277 }

assetsZooFadersLTPZooFadersLTPBlocksLTPFreestyleConsoleCH434d0 OBJECT IDENTIFIER ::= { assetsZooFadersLTPZooFadersLTPBlocksLTPFreestyleConsolec0ad 29380 }
-- MQTT: OPEN-AIR/Assets/Zoo/Faders/LTP/Zoo_Faders_LTP/blocks/LTP_Freestyle_Console/CH4/rotation
assetsZooFadersLTPZooFadersLTPBlocksLTPFreestyleConsoleCH4Roc869 OBJECT-TYPE
    SYNTAX      DisplayString
    MAX-ACCESS  read-write
    STATUS      current
    DESCRIPTION "Source: OPEN-AIR/Assets/Zoo/Faders/LTP/Zoo_Faders_LTP/blocks/LTP_Freestyle_Console/CH4/rotation"
    ::= { assetsZooFadersLTPZooFadersLTPBlocksLTPFreestyleConsoleCH434d0 39955 }

-- MQTT: OPEN-AIR/Assets/Zoo/Faders/LTP/Zoo_Faders_LTP/blocks/LTP_Freestyle_Console/CH1
assetsZooFadersLTPZooFadersLTPBlocksLTPFreestyleConsoleCH144ba OBJECT-TYPE
    SYNTAX      DisplayString
    MAX-ACCESS  read-write
    STATUS      current
    DESCRIPTION "Source: OPEN-AIR/Assets/Zoo/Faders/LTP/Zoo_Faders_LTP/blocks/LTP_Freestyle_Console/CH1"
    ::= { assetsZooFadersLTPZooFadersLTPBlocksLTPFreestyleConsolec0ad 34379 }

-- MQTT: OPEN-AIR/Assets/Zoo/Faders/LTP/Zoo_Faders_LTP/blocks/LTP_Freestyle_Console/CH3
assetsZooFadersLTPZooFadersLTPBlocksLTPFreestyleConsoleCH3aab4 OBJECT-TYPE
    SYNTAX      DisplayString
    MAX-ACCESS  read-write
    STATUS      current
    DESCRIPTION "Source: OPEN-AIR/Assets/Zoo/Faders/LTP/Zoo_Faders_LTP/blocks/LTP_Freestyle_Console/CH3"
    ::= { assetsZooFadersLTPZooFadersLTPBlocksLTPFreestyleConsolec0ad 59239 }

assetsZooFadersLTPZooFadersLTPBlocksLTPDemoBottomeeb8 OBJECT IDENTIFIER ::= { assetsZooFadersLTPZooFadersLTPBlocksd630 14057 }
-- MQTT: OPEN-AIR/Assets/Zoo/Faders/LTP/Zoo_Faders_LTP/blocks/LTP_Demo_Bottom/H3
assetsZooFadersLTPZooFadersLTPBlocksLTPDemoBottomH33431 OBJECT-TYPE
    SYNTAX      DisplayString
    MAX-ACCESS  read-write
    STATUS      current
    DESCRIPTION "Source: OPEN-AIR/Assets/Zoo/Faders/LTP/Zoo_Faders_LTP/blocks/LTP_Demo_Bottom/H3"
    ::= { assetsZooFadersLTPZooFadersLTPBlocksLTPDemoBottomeeb8 6524 }

assetsZooFadersLTPZooFadersLTPBlocksLTPDemoBottomH24336 OBJECT IDENTIFIER ::= { assetsZooFadersLTPZooFadersLTPBlocksLTPDemoBottomeeb8 10730 }
-- MQTT: OPEN-AIR/Assets/Zoo/Faders/LTP/Zoo_Faders_LTP/blocks/LTP_Demo_Bottom/H2/rotation
assetsZooFadersLTPZooFadersLTPBlocksLTPDemoBottomH2Rotationfc41 OBJECT-TYPE
    SYNTAX      DisplayString
    MAX-ACCESS  read-write
    STATUS      current
    DESCRIPTION "Source: OPEN-AIR/Assets/Zoo/Faders/LTP/Zoo_Faders_LTP/blocks/LTP_Demo_Bottom/H2/rotation"
    ::= { assetsZooFadersLTPZooFadersLTPBlocksLTPDemoBottomH24336 34022 }

assetsZooFadersVertical9813 OBJECT IDENTIFIER ::= { assetsZooFadersee8d 1 }
assetsZooFadersVerticalFader9c0c OBJECT IDENTIFIER ::= { assetsZooFadersVertical9813 1 }
assetsZooFadersVerticalFaderZooFadersVerticalfadera7ce OBJECT IDENTIFIER ::= { assetsZooFadersVerticalFader9c0c 65143 }
assetsZooFadersVerticalFaderZooFadersVerticalfaderBlocks5b78 OBJECT IDENTIFIER ::= { assetsZooFadersVerticalFaderZooFadersVerticalfadera7ce 17178 }
assetsZooFadersVerticalFaderZooFadersVerticalfaderBlocksFadeb440 OBJECT IDENTIFIER ::= { assetsZooFadersVerticalFaderZooFadersVerticalfaderBlocks5b78 17763 }
-- MQTT: OPEN-AIR/Assets/Zoo/Faders/Vertical/fader/Zoo_Faders_Vertical_fader/blocks/Fader_Zoo_MASTER/m_3
assetsZooFadersVerticalFaderZooFadersVerticalfaderBlocksFade785e OBJECT-TYPE
    SYNTAX      DisplayString
    MAX-ACCESS  read-write
    STATUS      current
    DESCRIPTION "Source: OPEN-AIR/Assets/Zoo/Faders/Vertical/fader/Zoo_Faders_Vertical_fader/blocks/Fader_Zoo_MASTER/m_3"
    ::= { assetsZooFadersVerticalFaderZooFadersVerticalfaderBlocksFadeb440 14300 }

-- MQTT: OPEN-AIR/Assets/Zoo/Faders/Vertical/fader/Zoo_Faders_Vertical_fader/blocks/Fader_Zoo_MASTER/m_7
assetsZooFadersVerticalFaderZooFadersVerticalfaderBlocksFade7f33 OBJECT-TYPE
    SYNTAX      DisplayString
    MAX-ACCESS  read-write
    STATUS      current
    DESCRIPTION "Source: OPEN-AIR/Assets/Zoo/Faders/Vertical/fader/Zoo_Faders_Vertical_fader/blocks/Fader_Zoo_MASTER/m_7"
    ::= { assetsZooFadersVerticalFaderZooFadersVerticalfaderBlocksFadeb440 62405 }

assetsZooFadersDualfader10dc OBJECT IDENTIFIER ::= { assetsZooFadersee8d 2 }
assetsZooFadersDualfaderMoreDualFadersd472 OBJECT IDENTIFIER ::= { assetsZooFadersDualfader10dc 4 }
assetsZooFadersDualfaderMoreDualFadersZooFadersdualfaderMore291c OBJECT IDENTIFIER ::= { assetsZooFadersDualfaderMoreDualFadersd472 61898 }
assetsZooFadersDualfaderMoreDualFadersZooFadersdualfaderMore153f OBJECT IDENTIFIER ::= { assetsZooFadersDualfaderMoreDualFadersZooFadersdualfaderMore291c 12958 }
assetsZooFadersDualfaderMoreDualFadersZooFadersdualfaderMorec453 OBJECT IDENTIFIER ::= { assetsZooFadersDualfaderMoreDualFadersZooFadersdualfaderMore153f 29634 }
assetsZooFadersDualfaderMoreDualFadersZooFadersdualfaderMore6633 OBJECT IDENTIFIER ::= { assetsZooFadersDualfaderMoreDualFadersZooFadersdualfaderMorec453 12885 }
-- MQTT: OPEN-AIR/Assets/Zoo/Faders/dual_fader/More_Dual_Faders/Zoo_Faders_dual_fader_More_Dual_Faders/blocks/Dual_Fader_Expansion/df_19/V2
assetsZooFadersDualfaderMoreDualFadersZooFadersdualfaderMore4535 OBJECT-TYPE
    SYNTAX      DisplayString
    MAX-ACCESS  read-write
    STATUS      current
    DESCRIPTION "Source: OPEN-AIR/Assets/Zoo/Faders/dual_fader/More_Dual_Faders/Zoo_Faders_dual_fader_More_Dual_Faders/blocks/Dual_Fader_Expansion/df_19/V2"
    ::= { assetsZooFadersDualfaderMoreDualFadersZooFadersdualfaderMore6633 36453 }

assetsZooFadersDualfaderMoreDualFadersZooFadersdualfaderMore34b8 OBJECT IDENTIFIER ::= { assetsZooFadersDualfaderMoreDualFadersZooFadersdualfaderMorec453 26615 }
-- MQTT: OPEN-AIR/Assets/Zoo/Faders/dual_fader/More_Dual_Faders/Zoo_Faders_dual_fader_More_Dual_Faders/blocks/Dual_Fader_Expansion/df_9/V1
assetsZooFadersDualfaderMoreDualFadersZooFadersdualfaderMorebb66 OBJECT-TYPE
    SYNTAX      DisplayString
    MAX-ACCESS  read-write
    STATUS      current
    DESCRIPTION "Source: OPEN-AIR/Assets/Zoo/Faders/dual_fader/More_Dual_Faders/Zoo_Faders_dual_fader_More_Dual_Faders/blocks/Dual_Fader_Expansion/df_9/V1"
    ::= { assetsZooFadersDualfaderMoreDualFadersZooFadersdualfaderMore34b8 42298 }

assetsZooFadersDualfaderMoreDualFadersZooFadersdualfaderMore68e8 OBJECT IDENTIFIER ::= { assetsZooFadersDualfaderMoreDualFadersZooFadersdualfaderMorec453 47719 }
-- MQTT: OPEN-AIR/Assets/Zoo/Faders/dual_fader/More_Dual_Faders/Zoo_Faders_dual_fader_More_Dual_Faders/blocks/Dual_Fader_Expansion/df_11/V1
assetsZooFadersDualfaderMoreDualFadersZooFadersdualfaderMore1988 OBJECT-TYPE
    SYNTAX      DisplayString
    MAX-ACCESS  read-write
    STATUS      current
    DESCRIPTION "Source: OPEN-AIR/Assets/Zoo/Faders/dual_fader/More_Dual_Faders/Zoo_Faders_dual_fader_More_Dual_Faders/blocks/Dual_Fader_Expansion/df_11/V1"
    ::= { assetsZooFadersDualfaderMoreDualFadersZooFadersdualfaderMore68e8 63280 }

assetsZooFadersDualfaderMoreDualFadersZooFadersdualfaderMore3a63 OBJECT IDENTIFIER ::= { assetsZooFadersDualfaderMoreDualFadersZooFadersdualfaderMorec453 61381 }
-- MQTT: OPEN-AIR/Assets/Zoo/Faders/dual_fader/More_Dual_Faders/Zoo_Faders_dual_fader_More_Dual_Faders/blocks/Dual_Fader_Expansion/df_1/V1
assetsZooFadersDualfaderMoreDualFadersZooFadersdualfaderMore7ed2 OBJECT-TYPE
    SYNTAX      DisplayString
    MAX-ACCESS  read-write
    STATUS      current
    DESCRIPTION "Source: OPEN-AIR/Assets/Zoo/Faders/dual_fader/More_Dual_Faders/Zoo_Faders_dual_fader_More_Dual_Faders/blocks/Dual_Fader_Expansion/df_1/V1"
    ::= { assetsZooFadersDualfaderMoreDualFadersZooFadersdualfaderMore3a63 36309 }

assetsZooFadersFaderDial8e1b OBJECT IDENTIFIER ::= { assetsZooFadersee8d 3 }
assetsZooFadersFaderDialClassicd14f OBJECT IDENTIFIER ::= { assetsZooFadersFaderDial8e1b 0 }
assetsZooFadersFaderDialClassicZooFadersFaderDialClassica38b OBJECT IDENTIFIER ::= { assetsZooFadersFaderDialClassicd14f 16231 }
assetsZooFadersFaderDialClassicZooFadersFaderDialClassicBlocf963 OBJECT IDENTIFIER ::= { assetsZooFadersFaderDialClassicZooFadersFaderDialClassica38b 21163 }
assetsZooFadersFaderDialClassicZooFadersFaderDialClassicBloc8f09 OBJECT IDENTIFIER ::= { assetsZooFadersFaderDialClassicZooFadersFaderDialClassicBlocf963 60664 }
assetsZooFadersFaderDialClassicZooFadersFaderDialClassicBlocb80a OBJECT IDENTIFIER ::= { assetsZooFadersFaderDialClassicZooFadersFaderDialClassicBloc8f09 17717 }
-- MQTT: OPEN-AIR/Assets/Zoo/Faders/Fader_Dial/Classic/Zoo_Faders_Fader_Dial_Classic/blocks/elements1/examplefields/dial_config
assetsZooFadersFaderDialClassicZooFadersFaderDialClassicBloc6f0d OBJECT-TYPE
    SYNTAX      DisplayString
    MAX-ACCESS  read-write
    STATUS      current
    DESCRIPTION "Source: OPEN-AIR/Assets/Zoo/Faders/Fader_Dial/Classic/Zoo_Faders_Fader_Dial_Classic/blocks/elements1/examplefields/dial_config"
    ::= { assetsZooFadersFaderDialClassicZooFadersFaderDialClassicBlocb80a 31105 }

-- MQTT: OPEN-AIR/Assets/Zoo/Faders/Fader_Dial/Classic/Zoo_Faders_Fader_Dial_Classic/blocks/elements1/examplefields/fader_config
assetsZooFadersFaderDialClassicZooFadersFaderDialClassicBloc900f OBJECT-TYPE
    SYNTAX      DisplayString
    MAX-ACCESS  read-write
    STATUS      current
    DESCRIPTION "Source: OPEN-AIR/Assets/Zoo/Faders/Fader_Dial/Classic/Zoo_Faders_Fader_Dial_Classic/blocks/elements1/examplefields/fader_config"
    ::= { assetsZooFadersFaderDialClassicZooFadersFaderDialClassicBlocb80a 46154 }

assetsZooFadersGCA45e9 OBJECT IDENTIFIER ::= { assetsZooFadersee8d 4 }
assetsZooFadersGCA5pointf58d OBJECT IDENTIFIER ::= { assetsZooFadersGCA45e9 2 }
assetsZooFadersGCA5pointZooFadersGCA5point1ee8f OBJECT IDENTIFIER ::= { assetsZooFadersGCA5pointf58d 31926 }
assetsZooFadersGCA5pointZooFadersGCA5point1Blockse1e5 OBJECT IDENTIFIER ::= { assetsZooFadersGCA5pointZooFadersGCA5point1ee8f 1208 }
assetsZooFadersGCA5pointZooFadersGCA5point1Blocks5pointOnec558 OBJECT IDENTIFIER ::= { assetsZooFadersGCA5pointZooFadersGCA5point1Blockse1e5 51553 }
assetsZooFadersGCA5pointZooFadersGCA5point1Blocks5pointOneCo2473 OBJECT IDENTIFIER ::= { assetsZooFadersGCA5pointZooFadersGCA5point1Blocks5pointOnec558 8677 }
-- MQTT: OPEN-AIR/Assets/Zoo/Faders/GCA/5point/Zoo_Faders_GCA_5point1/blocks/5 point One/composite_drums/ch_1
assetsZooFadersGCA5pointZooFadersGCA5point1Blocks5pointOneCod9fc OBJECT-TYPE
    SYNTAX      DisplayString
    MAX-ACCESS  read-write
    STATUS      current
    DESCRIPTION "Source: OPEN-AIR/Assets/Zoo/Faders/GCA/5point/Zoo_Faders_GCA_5point1/blocks/5 point One/composite_drums/ch_1"
    ::= { assetsZooFadersGCA5pointZooFadersGCA5point1Blocks5pointOneCo2473 31559 }

assetsZooFadersMDP6d8f OBJECT IDENTIFIER ::= { assetsZooFadersee8d 7 }
assetsZooFadersMDPZooFadersMDP28bd OBJECT IDENTIFIER ::= { assetsZooFadersMDP6d8f 59949 }
assetsZooFadersMDPZooFadersMDPBlocks4fd2 OBJECT IDENTIFIER ::= { assetsZooFadersMDPZooFadersMDP28bd 35100 }
assetsZooFadersMDPZooFadersMDPBlocksMdpdemode35 OBJECT IDENTIFIER ::= { assetsZooFadersMDPZooFadersMDPBlocks4fd2 21606 }
assetsZooFadersMDPZooFadersMDPBlocksMdpdemoMdp175fe OBJECT IDENTIFIER ::= { assetsZooFadersMDPZooFadersMDPBlocksMdpdemode35 5328 }
assetsZooFadersMDPZooFadersMDPBlocksMdpdemoMdp1Graph3b82 OBJECT IDENTIFIER ::= { assetsZooFadersMDPZooFadersMDPBlocksMdpdemoMdp175fe 707 }
assetsZooFadersMDPZooFadersMDPBlocksMdpdemoMdp1GraphOaDataRu55fd OBJECT IDENTIFIER ::= { assetsZooFadersMDPZooFadersMDPBlocksMdpdemoMdp1Graph3b82 57036 }
-- MQTT: OPEN-AIR/Assets/Zoo/Faders/MDP/Zoo_Faders_MDP/blocks/mdp_demo/mdp_1/graph/oaDataRunningFiles/MARKERS
assetsZooFadersMDPZooFadersMDPBlocksMdpdemoMdp1GraphOaDataRu7a5c OBJECT-TYPE
    SYNTAX      DisplayString
    MAX-ACCESS  read-write
    STATUS      current
    DESCRIPTION "Source: OPEN-AIR/Assets/Zoo/Faders/MDP/Zoo_Faders_MDP/blocks/mdp_demo/mdp_1/graph/oaDataRunningFiles/MARKERS"
    ::= { assetsZooFadersMDPZooFadersMDPBlocksMdpdemoMdp1GraphOaDataRu55fd 45295 }

-- MQTT: OPEN-AIR/Assets/Zoo/Faders/MDP/Zoo_Faders_MDP/blocks/mdp_demo/mdp_1/graph/oaDataRunningFiles/grid_ref
assetsZooFadersMDPZooFadersMDPBlocksMdpdemoMdp1GraphOaDataRue9a5 OBJECT-TYPE
    SYNTAX      DisplayString
    MAX-ACCESS  read-write
    STATUS      current
    DESCRIPTION "Source: OPEN-AIR/Assets/Zoo/Faders/MDP/Zoo_Faders_MDP/blocks/mdp_demo/mdp_1/graph/oaDataRunningFiles/grid_ref"
    ::= { assetsZooFadersMDPZooFadersMDPBlocksMdpdemoMdp1GraphOaDataRu55fd 55993 }

assetsZooFadersSlider5aa1 OBJECT IDENTIFIER ::= { assetsZooFadersee8d 10 }
assetsZooFadersSliderZooFadersslider7150 OBJECT IDENTIFIER ::= { assetsZooFadersSlider5aa1 8151 }
assetsZooFadersSliderZooFaderssliderBlocksacc2 OBJECT IDENTIFIER ::= { assetsZooFadersSliderZooFadersslider7150 10087 }
assetsZooFadersSliderZooFaderssliderBlocksFaderZooThresholde51d OBJECT IDENTIFIER ::= { assetsZooFadersSliderZooFaderssliderBlocksacc2 53015 }
-- MQTT: OPEN-AIR/Assets/Zoo/Faders/slider/Zoo_Faders_slider/blocks/Fader_Zoo_Threshold/fader_thr7
assetsZooFadersSliderZooFaderssliderBlocksFaderZooThresholdF76f0 OBJECT-TYPE
    SYNTAX      DisplayString
    MAX-ACCESS  read-write
    STATUS      current
    DESCRIPTION "Source: OPEN-AIR/Assets/Zoo/Faders/slider/Zoo_Faders_slider/blocks/Fader_Zoo_Threshold/fader_thr7"
    ::= { assetsZooFadersSliderZooFaderssliderBlocksFaderZooThresholde51d 2961 }

-- MQTT: OPEN-AIR/Assets/Zoo/Faders/slider/Zoo_Faders_slider/blocks/Fader_Zoo_Threshold/fader_thr2
assetsZooFadersSliderZooFaderssliderBlocksFaderZooThresholdF7705 OBJECT-TYPE
    SYNTAX      DisplayString
    MAX-ACCESS  read-write
    STATUS      current
    DESCRIPTION "Source: OPEN-AIR/Assets/Zoo/Faders/slider/Zoo_Faders_slider/blocks/Fader_Zoo_Threshold/fader_thr2"
    ::= { assetsZooFadersSliderZooFaderssliderBlocksFaderZooThresholde51d 65310 }

assetsZooButtons3e81 OBJECT IDENTIFIER ::= { assetsZoo5f4e 1 }
assetsZooButtonsWinkd7d6 OBJECT IDENTIFIER ::= { assetsZooButtons3e81 1 }
assetsZooButtonsWinkBlacktowink1e91 OBJECT IDENTIFIER ::= { assetsZooButtonsWinkd7d6 11 }
assetsZooButtonsWinkBlacktowinkZoobuttonsWinkblacktowink670b OBJECT IDENTIFIER ::= { assetsZooButtonsWinkBlacktowink1e91 51198 }
assetsZooButtonsWinkBlacktowinkZoobuttonsWinkblacktowinkBloc323b OBJECT IDENTIFIER ::= { assetsZooButtonsWinkBlacktowinkZoobuttonsWinkblacktowink670b 13299 }
assetsZooButtonsWinkBlacktowinkZoobuttonsWinkblacktowinkBloc6c66 OBJECT IDENTIFIER ::= { assetsZooButtonsWinkBlacktowinkZoobuttonsWinkblacktowinkBloc323b 19875 }
-- MQTT: OPEN-AIR/Assets/Zoo/buttons/Wink/black_to_wink/Zoo_buttons_Wink_black_to_wink/blocks/Wink_Buttons_Demo_2/wink_20_square_sky
assetsZooButtonsWinkBlacktowinkZoobuttonsWinkblacktowinkBlocbb6b OBJECT-TYPE
    SYNTAX      DisplayString
    MAX-ACCESS  read-write
    STATUS      current
    DESCRIPTION "Source: OPEN-AIR/Assets/Zoo/buttons/Wink/black_to_wink/Zoo_buttons_Wink_black_to_wink/blocks/Wink_Buttons_Demo_2/wink_20_square_sky"
    ::= { assetsZooButtonsWinkBlacktowinkZoobuttonsWinkblacktowinkBloc6c66 15083 }

assetsZooButtonsTrapezoid7d91 OBJECT IDENTIFIER ::= { assetsZooButtons3e81 2 }
assetsZooButtonsTrapezoidMediaButtons5381 OBJECT IDENTIFIER ::= { assetsZooButtonsTrapezoid7d91 6 }
assetsZooButtonsTrapezoidMediaButtonsZoobuttonsTrapezoidMedida00 OBJECT IDENTIFIER ::= { assetsZooButtonsTrapezoidMediaButtons5381 60516 }
assetsZooButtonsTrapezoidMediaButtonsZoobuttonsTrapezoidMedi8c20 OBJECT IDENTIFIER ::= { assetsZooButtonsTrapezoidMediaButtonsZoobuttonsTrapezoidMedida00 18466 }
assetsZooButtonsTrapezoidMediaButtonsZoobuttonsTrapezoidMedi29ff OBJECT IDENTIFIER ::= { assetsZooButtonsTrapezoidMediaButtonsZoobuttonsTrapezoidMedi8c20 61624 }
assetsZooButtonsTrapezoidMediaButtonsZoobuttonsTrapezoidMedi6c7d OBJECT IDENTIFIER ::= { assetsZooButtonsTrapezoidMediaButtonsZoobuttonsTrapezoidMedi29ff 51374 }
assetsZooButtonsTrapezoidMediaButtonsZoobuttonsTrapezoidMedi18bb OBJECT IDENTIFIER ::= { assetsZooButtonsTrapezoidMediaButtonsZoobuttonsTrapezoidMedi6c7d 29026 }
-- MQTT: OPEN-AIR/Assets/Zoo/buttons/Trapezoid/Media_Buttons/Zoo_buttons_Trapezoid_Media_Buttons/blocks/media_and_specialty/buttons_panel/momentary_grid/btn_m_14
assetsZooButtonsTrapezoidMediaButtonsZoobuttonsTrapezoidMedi2fc8 OBJECT-TYPE
    SYNTAX      DisplayString
    MAX-ACCESS  read-write
    STATUS      current
    DESCRIPTION "Source: OPEN-AIR/Assets/Zoo/buttons/Trapezoid/Media_Buttons/Zoo_buttons_Trapezoid_Media_Buttons/blocks/media_and_specialty/buttons_panel/momentary_grid/btn_m_14"
    ::= { assetsZooButtonsTrapezoidMediaButtonsZoobuttonsTrapezoidMedi18bb 10950 }

-- MQTT: OPEN-AIR/Assets/Zoo/buttons/Trapezoid/Media_Buttons/Zoo_buttons_Trapezoid_Media_Buttons/blocks/media_and_specialty/buttons_panel/momentary_grid/btn_m_16
assetsZooButtonsTrapezoidMediaButtonsZoobuttonsTrapezoidMedic1c6 OBJECT-TYPE
    SYNTAX      DisplayString
    MAX-ACCESS  read-write
    STATUS      current
    DESCRIPTION "Source: OPEN-AIR/Assets/Zoo/buttons/Trapezoid/Media_Buttons/Zoo_buttons_Trapezoid_Media_Buttons/blocks/media_and_specialty/buttons_panel/momentary_grid/btn_m_16"
    ::= { assetsZooButtonsTrapezoidMediaButtonsZoobuttonsTrapezoidMedi18bb 19434 }

assetsZooButtonsTrapezoidTrapezoidbutton21e9 OBJECT IDENTIFIER ::= { assetsZooButtonsTrapezoid7d91 9 }
assetsZooButtonsTrapezoidTrapezoidbuttonZoobuttonsTrapezoidt919c OBJECT IDENTIFIER ::= { assetsZooButtonsTrapezoidTrapezoidbutton21e9 23562 }
assetsZooButtonsTrapezoidTrapezoidbuttonZoobuttonsTrapezoidt1580 OBJECT IDENTIFIER ::= { assetsZooButtonsTrapezoidTrapezoidbuttonZoobuttonsTrapezoidt919c 31170 }
assetsZooButtonsTrapezoidTrapezoidbuttonZoobuttonsTrapezoidt9310 OBJECT IDENTIFIER ::= { assetsZooButtonsTrapezoidTrapezoidbuttonZoobuttonsTrapezoidt1580 1237 }
-- MQTT: OPEN-AIR/Assets/Zoo/buttons/Trapezoid/trapezoid_button/Zoo_buttons_Trapezoid_trapezoid_button_2/blocks/Trapezoid_Button_MUTE_Variations/power_momentary_orange
assetsZooButtonsTrapezoidTrapezoidbuttonZoobuttonsTrapezoidtf505 OBJECT-TYPE
    SYNTAX      DisplayString
    MAX-ACCESS  read-write
    STATUS      current
    DESCRIPTION "Source: OPEN-AIR/Assets/Zoo/buttons/Trapezoid/trapezoid_button/Zoo_buttons_Trapezoid_trapezoid_button_2/blocks/Trapezoid_Button_MUTE_Variations/power_momentary_orange"
    ::= { assetsZooButtonsTrapezoidTrapezoidbuttonZoobuttonsTrapezoidt9310 12803 }

-- MQTT: OPEN-AIR/Assets/Zoo/buttons/Trapezoid/trapezoid_button/Zoo_buttons_Trapezoid_trapezoid_button_2/blocks/Trapezoid_Button_MUTE_Variations/bypass_momentary_green
assetsZooButtonsTrapezoidTrapezoidbuttonZoobuttonsTrapezoidt298c OBJECT-TYPE
    SYNTAX      DisplayString
    MAX-ACCESS  read-write
    STATUS      current
    DESCRIPTION "Source: OPEN-AIR/Assets/Zoo/buttons/Trapezoid/trapezoid_button/Zoo_buttons_Trapezoid_trapezoid_button_2/blocks/Trapezoid_Button_MUTE_Variations/bypass_momentary_green"
    ::= { assetsZooButtonsTrapezoidTrapezoidbuttonZoobuttonsTrapezoidt9310 34926 }

assetsZooButtonsTrapezoidTrapezoidbuttonZoobuttonsTrapezoidt6c6d OBJECT IDENTIFIER ::= { assetsZooButtonsTrapezoidTrapezoidbuttonZoobuttonsTrapezoidt1580 62916 }
-- MQTT: OPEN-AIR/Assets/Zoo/buttons/Trapezoid/trapezoid_button/Zoo_buttons_Trapezoid_trapezoid_button_2/blocks/elements5/examplefields
assetsZooButtonsTrapezoidTrapezoidbuttonZoobuttonsTrapezoidt9f38 OBJECT-TYPE
    SYNTAX      DisplayString
    MAX-ACCESS  read-write
    STATUS      current
    DESCRIPTION "Source: OPEN-AIR/Assets/Zoo/buttons/Trapezoid/trapezoid_button/Zoo_buttons_Trapezoid_trapezoid_button_2/blocks/elements5/examplefields"
    ::= { assetsZooButtonsTrapezoidTrapezoidbuttonZoobuttonsTrapezoidt6c6d 44623 }

assetsZooButtonsTrapezoidTrapezoidbuttonZoobuttonsTrapezoidt37d0 OBJECT IDENTIFIER ::= { assetsZooButtonsTrapezoidTrapezoidbutton21e9 30701 }
assetsZooButtonsTrapezoidTrapezoidbuttonZoobuttonsTrapezoidt4bef OBJECT IDENTIFIER ::= { assetsZooButtonsTrapezoidTrapezoidbuttonZoobuttonsTrapezoidt37d0 59199 }
assetsZooButtonsTrapezoidTrapezoidbuttonZoobuttonsTrapezoidt14bb OBJECT IDENTIFIER ::= { assetsZooButtonsTrapezoidTrapezoidbuttonZoobuttonsTrapezoidt4bef 51371 }
-- MQTT: OPEN-AIR/Assets/Zoo/buttons/Trapezoid/trapezoid_button/Zoo_buttons_Trapezoid_trapezoid_button/blocks/Trapezoid_Button_Petting_Zoo/mode_cyan_wide
assetsZooButtonsTrapezoidTrapezoidbuttonZoobuttonsTrapezoidt3396 OBJECT-TYPE
    SYNTAX      DisplayString
    MAX-ACCESS  read-write
    STATUS      current
    DESCRIPTION "Source: OPEN-AIR/Assets/Zoo/buttons/Trapezoid/trapezoid_button/Zoo_buttons_Trapezoid_trapezoid_button/blocks/Trapezoid_Button_Petting_Zoo/mode_cyan_wide"
    ::= { assetsZooButtonsTrapezoidTrapezoidbuttonZoobuttonsTrapezoidt14bb 25750 }

assetsZooButtonsTrapezoidTrapezoidbuttonZoobuttonsTrapezoidt95e8 OBJECT IDENTIFIER ::= { assetsZooButtonsTrapezoidTrapezoidbuttonZoobuttonsTrapezoidt4bef 53182 }
-- MQTT: OPEN-AIR/Assets/Zoo/buttons/Trapezoid/trapezoid_button/Zoo_buttons_Trapezoid_trapezoid_button/blocks/Trapezoid_Button_REC_Variations/rec_demo3
assetsZooButtonsTrapezoidTrapezoidbuttonZoobuttonsTrapezoidt3b70 OBJECT-TYPE
    SYNTAX      DisplayString
    MAX-ACCESS  read-write
    STATUS      current
    DESCRIPTION "Source: OPEN-AIR/Assets/Zoo/buttons/Trapezoid/trapezoid_button/Zoo_buttons_Trapezoid_trapezoid_button/blocks/Trapezoid_Button_REC_Variations/rec_demo3"
    ::= { assetsZooButtonsTrapezoidTrapezoidbuttonZoobuttonsTrapezoidt95e8 4368 }

assetsZooButtonsTrapezoidTrapezoidtoggler2733 OBJECT IDENTIFIER ::= { assetsZooButtonsTrapezoid7d91 10 }
assetsZooButtonsTrapezoidTrapezoidtogglerZoobuttonsTrapezoidb9a0 OBJECT IDENTIFIER ::= { assetsZooButtonsTrapezoidTrapezoidtoggler2733 14795 }
assetsZooButtonsTrapezoidTrapezoidtogglerZoobuttonsTrapezoid2684 OBJECT IDENTIFIER ::= { assetsZooButtonsTrapezoidTrapezoidtogglerZoobuttonsTrapezoidb9a0 41282 }
assetsZooButtonsTrapezoidTrapezoidtogglerZoobuttonsTrapezoidf273 OBJECT IDENTIFIER ::= { assetsZooButtonsTrapezoidTrapezoidtogglerZoobuttonsTrapezoid2684 26230 }
-- MQTT: OPEN-AIR/Assets/Zoo/buttons/Trapezoid/trapezoid_toggler/Zoo_buttons_Trapezoid_trapezoid_toggler/blocks/Trapezoid_Toggler_Demos/toggler_mode_latching
assetsZooButtonsTrapezoidTrapezoidtogglerZoobuttonsTrapezoid2e1e OBJECT-TYPE
    SYNTAX      DisplayString
    MAX-ACCESS  read-write
    STATUS      current
    DESCRIPTION "Source: OPEN-AIR/Assets/Zoo/buttons/Trapezoid/trapezoid_toggler/Zoo_buttons_Trapezoid_trapezoid_toggler/blocks/Trapezoid_Toggler_Demos/toggler_mode_latching"
    ::= { assetsZooButtonsTrapezoidTrapezoidtogglerZoobuttonsTrapezoidf273 2235 }

assetsZooKnobs18ae OBJECT IDENTIFIER ::= { assetsZoo5f4e 2 }
assetsZooKnobsKnobs618b OBJECT IDENTIFIER ::= { assetsZooKnobs18ae 0 }
assetsZooKnobsKnobsGearknobsab8d OBJECT IDENTIFIER ::= { assetsZooKnobsKnobs618b 1 }
assetsZooKnobsKnobsGearknobsZooKnobsknobsGearknobs5148 OBJECT IDENTIFIER ::= { assetsZooKnobsKnobsGearknobsab8d 17806 }
assetsZooKnobsKnobsGearknobsZooKnobsknobsGearknobsBlocks4738 OBJECT IDENTIFIER ::= { assetsZooKnobsKnobsGearknobsZooKnobsknobsGearknobs5148 54255 }
assetsZooKnobsKnobsGearknobsZooKnobsknobsGearknobsBlocksKnob199a OBJECT IDENTIFIER ::= { assetsZooKnobsKnobsGearknobsZooKnobsknobsGearknobsBlocks4738 242 }
-- MQTT: OPEN-AIR/Assets/Zoo/Knobs/knobs/Gear_knobs/Zoo_Knobs_knobs_Gear_knobs/blocks/Knob_Showcase_Gear_Advanced/gear_04
assetsZooKnobsKnobsGearknobsZooKnobsknobsGearknobsBlocksKnobc369 OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_04"
    ::= { assetsZooKnobsKnobsGearknobsZooKnobsknobsGearknobsBlocksKnob199a 3537 }

-- MQTT: OPEN-AIR/Assets/Zoo/Knobs/knobs/Gear_knobs/Zoo_Knobs_knobs_Gear_knobs/blocks/Knob_Showcase_Gear_Advanced/gear_14
assetsZooKnobsKnobsGearknobsZooKnobsknobsGearknobsBlocksKnobda72 OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_14"
    ::= { assetsZooKnobsKnobsGearknobsZooKnobsknobsGearknobsBlocksKnob199a 15504 }

-- MQTT: OPEN-AIR/Assets/Zoo/Knobs/knobs/Gear_knobs/Zoo_Knobs_knobs_Gear_knobs/blocks/Knob_Showcase_Gear_Advanced/gear_05
assetsZooKnobsKnobsGearknobsZooKnobsknobsGearknobsBlocksKnobb46e OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_05"
    ::= { assetsZooKnobsKnobsGearknobsZooKnobsknobsGearknobsBlocksKnob199a 15687 }

-- MQTT: OPEN-AIR/Assets/Zoo/Knobs/knobs/Gear_knobs/Zoo_Knobs_knobs_Gear_knobs/blocks/Knob_Showcase_Gear_Advanced/gear_06
assetsZooKnobsKnobsGearknobsZooKnobsknobsGearknobsBlocksKnob2d67 OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_06"
    ::= { assetsZooKnobsKnobsGearknobsZooKnobsknobsGearknobsBlocksKnob199a 27901 }

-- MQTT: OPEN-AIR/Assets/Zoo/Knobs/knobs/Gear_knobs/Zoo_Knobs_knobs_Gear_knobs/blocks/Knob_Showcase_Gear_Advanced/gear_18
assetsZooKnobsKnobsGearknobsZooKnobsknobsGearknobsBlocksKnobd3c4 OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_18"
    ::= { assetsZooKnobsKnobsGearknobsZooKnobsknobsGearknobsBlocksKnob199a 28859 }

-- MQTT: OPEN-AIR/Assets/Zoo/Knobs/knobs/Gear_knobs/Zoo_Knobs_knobs_Gear_knobs/blocks/Knob_Showcase_Gear_Advanced/gear_02
assetsZooKnobsKnobsGearknobsZooKnobsknobsGearknobsBlocksKnob2a0a OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_02"
    ::= { assetsZooKnobsKnobsGearknobsZooKnobsknobsGearknobsBlocksKnob199a 43236 }

-- MQTT: OPEN-AIR/Assets/Zoo/Knobs/knobs/Gear_knobs/Zoo_Knobs_knobs_Gear_knobs/blocks/Knob_Showcase_Gear_Advanced/gear_10
assetsZooKnobsKnobsGearknobsZooKnobsknobsGearknobsBlocksKnobdd1f OBJECT-TYPE
    SYNTAX      DisplayString
    MAX-ACCESS  read-write
    STATUS      current
    DESCRIPTION "Source: OPEN-AIR/Assets/Zoo/Knobs/knobs/Gear_knobs/Zoo_Knobs_knobs_Gear_knobs/blocks/Knob_Showcase_Gear_Advanced/gear_10"
    ::= { assetsZooKnobsKnobsGearknobsZooKnobsknobsGearknobsBlocksKnob199a 63625 }

assetsZooKnobsKnobsKnobdee0 OBJECT IDENTIFIER ::= { assetsZooKnobsKnobs618b 5 }
assetsZooKnobsKnobsKnobZooKnobsknobsknob1e56a OBJECT IDENTIFIER ::= { assetsZooKnobsKnobsKnobdee0 1355 }
assetsZooKnobsKnobsKnobZooKnobsknobsknob1Blocksff54 OBJECT IDENTIFIER ::= { assetsZooKnobsKnobsKnobZooKnobsknobsknob1e56a 52230 }
assetsZooKnobsKnobsKnobZooKnobsknobsknob1BlocksKnobZooDrive51bf OBJECT IDENTIFIER ::= { assetsZooKnobsKnobsKnobZooKnobsknobsknob1Blocksff54 37669 }
-- MQTT: OPEN-AIR/Assets/Zoo/Knobs/knobs/knob/Zoo_Knobs_knobs_knob_1/blocks/Knob_Zoo_Drive/knob_drv1
assetsZooKnobsKnobsKnobZooKnobsknobsknob1BlocksKnobZooDriveKdf98 OBJECT-TYPE
    SYNTAX      DisplayString
    MAX-ACCESS  read-write
    STATUS      current
    DESCRIPTION "Source: OPEN-AIR/Assets/Zoo/Knobs/knobs/knob/Zoo_Knobs_knobs_knob_1/blocks/Knob_Zoo_Drive/knob_drv1"
    ::= { assetsZooKnobsKnobsKnobZooKnobsknobsknob1BlocksKnobZooDrive51bf 50651 }

assetsZooKnobsKnobsKnobZooKnobsknobsknob1BlocksKnobZooAdvanc631e OBJECT IDENTIFIER ::= { assetsZooKnobsKnobsKnobZooKnobsknobsknob1Blocksff54 48667 }
-- MQTT: OPEN-AIR/Assets/Zoo/Knobs/knobs/knob/Zoo_Knobs_knobs_knob_1/blocks/Knob_Zoo_Advanced/knob_adv4
assetsZooKnobsKnobsKnobZooKnobsknobsknob1BlocksKnobZooAdvancdc18 OBJECT-TYPE
    SYNTAX      DisplayString
    MAX-ACCESS  read-write
    STATUS      current
    DESCRIPTION "Source: OPEN-AIR/Assets/Zoo/Knobs/knobs/knob/Zoo_Knobs_knobs_knob_1/blocks/Knob_Zoo_Advanced/knob_adv4"
    ::= { assetsZooKnobsKnobsKnobZooKnobsknobsknob1BlocksKnobZooAdvanc631e 39602 }

assetsZooKnobsKnobsKnobZooKnobsknobsknob27c63 OBJECT IDENTIFIER ::= { assetsZooKnobsKnobsKnobdee0 21745 }
assetsZooKnobsKnobsKnobZooKnobsknobsknob2Blocks71db OBJECT IDENTIFIER ::= { assetsZooKnobsKnobsKnobZooKnobsknobsknob27c63 52197 }
assetsZooKnobsKnobsKnobZooKnobsknobsknob2BlocksKnobCombinedDba93 OBJECT IDENTIFIER ::= { assetsZooKnobsKnobsKnobZooKnobsknobsknob2Blocks71db 1750 }
-- MQTT: OPEN-AIR/Assets/Zoo/Knobs/knobs/knob/Zoo_Knobs_knobs_knob_2/blocks/Knob_Combined_Demo_2/knob_f6
assetsZooKnobsKnobsKnobZooKnobsknobsknob2BlocksKnobCombinedD8dac OBJECT-TYPE
    SYNTAX      DisplayString
    MAX-ACCESS  read-write
    STATUS      current
    DESCRIPTION "Source: OPEN-AIR/Assets/Zoo/Knobs/knobs/knob/Zoo_Knobs_knobs_knob_2/blocks/Knob_Combined_Demo_2/knob_f6"
    ::= { assetsZooKnobsKnobsKnobZooKnobsknobsknob2BlocksKnobCombinedDba93 2174 }

-- MQTT: OPEN-AIR/Assets/Zoo/Knobs/knobs/knob/Zoo_Knobs_knobs_knob_2/blocks/Knob_Combined_Demo_2/knob_04
assetsZooKnobsKnobsKnobZooKnobsknobsknob2BlocksKnobCombinedD8f43 OBJECT-TYPE
    SYNTAX      DisplayString
    MAX-ACCESS  read-write
    STATUS      current
    DESCRIPTION "Source: OPEN-AIR/Assets/Zoo/Knobs/knobs/knob/Zoo_Knobs_knobs_knob_2/blocks/Knob_Combined_Demo_2/knob_04"
    ::= { assetsZooKnobsKnobsKnobZooKnobsknobsknob2BlocksKnobCombinedDba93 37760 }

assetsZooKnobsKnobsKnobZooKnobsknobsknob3b646 OBJECT IDENTIFIER ::= { assetsZooKnobsKnobsKnobdee0 25703 }
assetsZooKnobsKnobsKnobZooKnobsknobsknob3Blocksbd71 OBJECT IDENTIFIER ::= { assetsZooKnobsKnobsKnobZooKnobsknobsknob3b646 52091 }
assetsZooKnobsKnobsKnobZooKnobsknobsknob3BlocksKnobCombinedD5255 OBJECT IDENTIFIER ::= { assetsZooKnobsKnobsKnobZooKnobsknobsknob3Blocksbd71 54553 }
-- MQTT: OPEN-AIR/Assets/Zoo/Knobs/knobs/knob/Zoo_Knobs_knobs_knob_3/blocks/Knob_Combined_Demo/knob_02
assetsZooKnobsKnobsKnobZooKnobsknobsknob3BlocksKnobCombinedD8098 OBJECT-TYPE
    SYNTAX      DisplayString
    MAX-ACCESS  read-write
    STATUS      current
    DESCRIPTION "Source: OPEN-AIR/Assets/Zoo/Knobs/knobs/knob/Zoo_Knobs_knobs_knob_3/blocks/Knob_Combined_Demo/knob_02"
    ::= { assetsZooKnobsKnobsKnobZooKnobsknobsknob3BlocksKnobCombinedD5255 2881 }

assetsZooKnobsKnobsKnobs1bd0 OBJECT IDENTIFIER ::= { assetsZooKnobsKnobs618b 5 }
assetsZooKnobsKnobsKnobsZooKnobsknobsknobs53ae8 OBJECT IDENTIFIER ::= { assetsZooKnobsKnobsKnobs1bd0 48992 }
assetsZooKnobsKnobsKnobsZooKnobsknobsknobs5Blocks3cae OBJECT IDENTIFIER ::= { assetsZooKnobsKnobsKnobsZooKnobsknobsknobs53ae8 56142 }
assetsZooKnobsKnobsKnobsZooKnobsknobsknobs5BlocksKnobOverhau7d25 OBJECT IDENTIFIER ::= { assetsZooKnobsKnobsKnobsZooKnobsknobsknobs5Blocks3cae 7328 }
-- MQTT: OPEN-AIR/Assets/Zoo/Knobs/knobs/knobs/Zoo_Knobs_knobs_knobs_5/blocks/Knob_Overhaul_Showcase/knob_078
assetsZooKnobsKnobsKnobsZooKnobsknobsknobs5BlocksKnobOverhau1d90 OBJECT-TYPE
    SYNTAX      DisplayString
    MAX-ACCESS  read-write
    STATUS      current
    DESCRIPTION "Source: OPEN-AIR/Assets/Zoo/Knobs/knobs/knobs/Zoo_Knobs_knobs_knobs_5/blocks/Knob_Overhaul_Showcase/knob_078"
    ::= { assetsZooKnobsKnobsKnobsZooKnobsknobsknobs5BlocksKnobOverhau7d25 1865 }

-- MQTT: OPEN-AIR/Assets/Zoo/Knobs/knobs/knobs/Zoo_Knobs_knobs_knobs_5/blocks/Knob_Overhaul_Showcase/knob_032
assetsZooKnobsKnobsKnobsZooKnobsknobsknobs5BlocksKnobOverhau9929 OBJECT-TYPE
    SYNTAX      DisplayString
    MAX-ACCESS  read-write
    STATUS      current
    DESCRIPTION "Source: OPEN-AIR/Assets/Zoo/Knobs/knobs/knobs/Zoo_Knobs_knobs_knobs_5/blocks/Knob_Overhaul_Showcase/knob_032"
    ::= { assetsZooKnobsKnobsKnobsZooKnobsknobsknobs5BlocksKnobOverhau7d25 11091 }

-- MQTT: OPEN-AIR/Assets/Zoo/Knobs/knobs/knobs/Zoo_Knobs_knobs_knobs_5/blocks/Knob_Overhaul_Showcase/knob_095
assetsZooKnobsKnobsKnobsZooKnobsknobsknobs5BlocksKnobOverhaufda2 OBJECT-TYPE
    SYNTAX      DisplayString
    MAX-ACCESS  read-write
    STATUS      current
    DESCRIPTION "Source: OPEN-AIR/Assets/Zoo/Knobs/knobs/knobs/Zoo_Knobs_knobs_knobs_5/blocks/Knob_Overhaul_Showcase/knob_095"
    ::= { assetsZooKnobsKnobsKnobsZooKnobsknobsknobs5BlocksKnobOverhau7d25 22138 }

-- MQTT: OPEN-AIR/Assets/Zoo/Knobs/knobs/knobs/Zoo_Knobs_knobs_knobs_5/blocks/Knob_Overhaul_Showcase/knob_100
assetsZooKnobsKnobsKnobsZooKnobsknobsknobs5BlocksKnobOverhau5dc8 OBJECT-TYPE
    SYNTAX      DisplayString
    MAX-ACCESS  read-write
    STATUS      current
    DESCRIPTION "Source: OPEN-AIR/Assets/Zoo/Knobs/knobs/knobs/Zoo_Knobs_knobs_knobs_5/blocks/Knob_Overhaul_Showcase/knob_100"
    ::= { assetsZooKnobsKnobsKnobsZooKnobsknobsknobs5BlocksKnobOverhau7d25 29579 }

-- MQTT: OPEN-AIR/Assets/Zoo/Knobs/knobs/knobs/Zoo_Knobs_knobs_knobs_5/blocks/Knob_Overhaul_Showcase/knob_019
assetsZooKnobsKnobsKnobsZooKnobsknobsknobs5BlocksKnobOverhau3ccd OBJECT-TYPE
    SYNTAX      DisplayString
    MAX-ACCESS  read-write
    STATUS      current
    DESCRIPTION "Source: OPEN-AIR/Assets/Zoo/Knobs/knobs/knobs/Zoo_Knobs_knobs_knobs_5/blocks/Knob_Overhaul_Showcase/knob_019"
    ::= { assetsZooKnobsKnobsKnobsZooKnobsknobsknobs5BlocksKnobOverhau7d25 36953 }

-- MQTT: OPEN-AIR/Assets/Zoo/Knobs/knobs/knobs/Zoo_Knobs_knobs_knobs_5/blocks/Knob_Overhaul_Showcase/knob_092
assetsZooKnobsKnobsKnobsZooKnobsknobsknobs5BlocksKnobOverhau63c6 OBJECT-TYPE
    SYNTAX      DisplayString
    MAX-ACCESS  read-write
    STATUS      current
    DESCRIPTION "Source: OPEN-AIR/Assets/Zoo/Knobs/knobs/knobs/Zoo_Knobs_knobs_knobs_5/blocks/Knob_Overhaul_Showcase/knob_092"
    ::= { assetsZooKnobsKnobsKnobsZooKnobsknobsknobs5BlocksKnobOverhau7d25 50137 }

assetsZooKnobsKnobsKnobsZooKnobsknobsknobs7d4e6 OBJECT IDENTIFIER ::= { assetsZooKnobsKnobsKnobs1bd0 56908 }
assetsZooKnobsKnobsKnobsZooKnobsknobsknobs7Blocks7e8b OBJECT IDENTIFIER ::= { assetsZooKnobsKnobsKnobsZooKnobsknobsknobs7d4e6 56371 }
assetsZooKnobsKnobsKnobsZooKnobsknobsknobs7BlocksKnobShowcas3616 OBJECT IDENTIFIER ::= { assetsZooKnobsKnobsKnobsZooKnobsknobsknobs7Blocks7e8b 21765 }
-- MQTT: OPEN-AIR/Assets/Zoo/Knobs/knobs/knobs/Zoo_Knobs_knobs_knobs_7/blocks/Knob_Showcase_Ticks_Dials/knob_tk_28
assetsZooKnobsKnobsKnobsZooKnobsknobsknobs7BlocksKnobShowcasdb8a OBJECT-TYPE
    SYNTAX      DisplayString
    MAX-ACCESS  read-write
    STATUS      current
    DESCRIPTION "Source: OPEN-AIR/Assets/Zoo/Knobs/knobs/knobs/Zoo_Knobs_knobs_knobs_7/blocks/Knob_Showcase_Ticks_Dials/knob_tk_28"
    ::= { assetsZooKnobsKnobsKnobsZooKnobsknobsknobs7BlocksKnobShowcas3616 2453 }

assetsZooMetering32f2 OBJECT IDENTIFIER ::= { assetsZoo5f4e 2 }
assetsZooMeteringNeedlee83c OBJECT IDENTIFIER ::= { assetsZooMetering32f2 1 }
assetsZooMeteringNeedleREFa0d4 OBJECT IDENTIFIER ::= { assetsZooMeteringNeedlee83c 0 }
assetsZooMeteringNeedleREFZooMeteringNeedleREF3be8 OBJECT IDENTIFIER ::= { assetsZooMeteringNeedleREFa0d4 63181 }
assetsZooMeteringNeedleREFZooMeteringNeedleREFBlocks8a39 OBJECT IDENTIFIER ::= { assetsZooMeteringNeedleREFZooMeteringNeedleREF3be8 21793 }
assetsZooMeteringNeedleREFZooMeteringNeedleREFBlocksVintageA3431 OBJECT IDENTIFIER ::= { assetsZooMeteringNeedleREFZooMeteringNeedleREFBlocks8a39 14040 }
-- MQTT: OPEN-AIR/Assets/Zoo/Metering/Needle/REF/Zoo_Metering_Needle_REF/blocks/Vintage_Aesthetics/Vintage_Night
assetsZooMeteringNeedleREFZooMeteringNeedleREFBlocksVintageA5dbb OBJECT-TYPE
    SYNTAX      DisplayString
    MAX-ACCESS  read-write
    STATUS      current
    DESCRIPTION "Source: OPEN-AIR/Assets/Zoo/Metering/Needle/REF/Zoo_Metering_Needle_REF/blocks/Vintage_Aesthetics/Vintage_Night"
    ::= { assetsZooMeteringNeedleREFZooMeteringNeedleREFBlocksVintageA3431 36628 }

assetsZooMeteringNeedleREFZooMeteringNeedleREFBlocksHardware8551 OBJECT IDENTIFIER ::= { assetsZooMeteringNeedleREFZooMeteringNeedleREFBlocks8a39 33507 }
-- MQTT: OPEN-AIR/Assets/Zoo/Metering/Needle/REF/Zoo_Metering_Needle_REF/blocks/Hardware_Scales_1/Scale_ABC_East
assetsZooMeteringNeedleREFZooMeteringNeedleREFBlocksHardware2cc8 OBJECT-TYPE
    SYNTAX      DisplayString
    MAX-ACCESS  read-write
    STATUS      current
    DESCRIPTION "Source: OPEN-AIR/Assets/Zoo/Metering/Needle/REF/Zoo_Metering_Needle_REF/blocks/Hardware_Scales_1/Scale_ABC_East"
    ::= { assetsZooMeteringNeedleREFZooMeteringNeedleREFBlocksHardware8551 22714 }

assetsZooMeteringBarMetera475 OBJECT IDENTIFIER ::= { assetsZooMetering32f2 2 }
assetsZooMeteringBarMeterREFee1c OBJECT IDENTIFIER ::= { assetsZooMeteringBarMetera475 0 }
assetsZooMeteringBarMeterREFZooMeteringBarMeterREF29d0 OBJECT IDENTIFIER ::= { assetsZooMeteringBarMeterREFee1c 444 }
assetsZooMeteringBarMeterREFZooMeteringBarMeterREFBlocksa3f0 OBJECT IDENTIFIER ::= { assetsZooMeteringBarMeterREFZooMeteringBarMeterREF29d0 52044 }
assetsZooMeteringBarMeterREFZooMeteringBarMeterREFBlocksDigi8e9c OBJECT IDENTIFIER ::= { assetsZooMeteringBarMeterREFZooMeteringBarMeterREFBlocksa3f0 26 }
-- MQTT: OPEN-AIR/Assets/Zoo/Metering/Bar_Meter/REF/Zoo_Metering_Bar_Meter_REF/blocks/Digital_Meters_Bar/LUFS_ShortTerm_Bar
assetsZooMeteringBarMeterREFZooMeteringBarMeterREFBlocksDigi8b0b OBJECT-TYPE
    SYNTAX      DisplayString
    MAX-ACCESS  read-write
    STATUS      current
    DESCRIPTION "Source: OPEN-AIR/Assets/Zoo/Metering/Bar_Meter/REF/Zoo_Metering_Bar_Meter_REF/blocks/Digital_Meters_Bar/LUFS_ShortTerm_Bar"
    ::= { assetsZooMeteringBarMeterREFZooMeteringBarMeterREFBlocksDigi8e9c 38468 }

assetsZooMeteringBarMeterREFZooMeteringBarMeterREFBlocksAverdcc1 OBJECT IDENTIFIER ::= { assetsZooMeteringBarMeterREFZooMeteringBarMeterREFBlocksa3f0 44892 }
-- MQTT: OPEN-AIR/Assets/Zoo/Metering/Bar_Meter/REF/Zoo_Metering_Bar_Meter_REF/blocks/Averaging_Meters_Bar/Standard_VU_Bar
assetsZooMeteringBarMeterREFZooMeteringBarMeterREFBlocksAver657c OBJECT-TYPE
    SYNTAX      DisplayString
    MAX-ACCESS  read-write
    STATUS      current
    DESCRIPTION "Source: OPEN-AIR/Assets/Zoo/Metering/Bar_Meter/REF/Zoo_Metering_Bar_Meter_REF/blocks/Averaging_Meters_Bar/Standard_VU_Bar"
    ::= { assetsZooMeteringBarMeterREFZooMeteringBarMeterREFBlocksAverdcc1 48687 }

assetsZooMeteringBarMeterREFZooMeteringBarMeterREFBlocksProt2c22 OBJECT IDENTIFIER ::= { assetsZooMeteringBarMeterREFZooMeteringBarMeterREFBlocksa3f0 49667 }
-- MQTT: OPEN-AIR/Assets/Zoo/Metering/Bar_Meter/REF/Zoo_Metering_Bar_Meter_REF/blocks/Protection_Meters_Bar/PPM_Type_I_Bar
assetsZooMeteringBarMeterREFZooMeteringBarMeterREFBlocksProt5f28 OBJECT-TYPE
    SYNTAX      DisplayString
    MAX-ACCESS  read-write
    STATUS      current
    DESCRIPTION "Source: OPEN-AIR/Assets/Zoo/Metering/Bar_Meter/REF/Zoo_Metering_Bar_Meter_REF/blocks/Protection_Meters_Bar/PPM_Type_I_Bar"
    ::= { assetsZooMeteringBarMeterREFZooMeteringBarMeterREFBlocksProt2c22 60621 }

assetsZooMeteringBarMeterHorizontalbar3345 OBJECT IDENTIFIER ::= { assetsZooMeteringBarMetera475 1 }
assetsZooMeteringBarMeterHorizontalbarZooMeteringBarMeterHora74f OBJECT IDENTIFIER ::= { assetsZooMeteringBarMeterHorizontalbar3345 37046 }
assetsZooMeteringBarMeterHorizontalbarZooMeteringBarMeterHor8f6a OBJECT IDENTIFIER ::= { assetsZooMeteringBarMeterHorizontalbarZooMeteringBarMeterHora74f 8237 }
assetsZooMeteringBarMeterHorizontalbarZooMeteringBarMeterHor6770 OBJECT IDENTIFIER ::= { assetsZooMeteringBarMeterHorizontalbarZooMeteringBarMeterHor8f6a 22378 }
-- MQTT: OPEN-AIR/Assets/Zoo/Metering/Bar_Meter/Horizontal_bar/Zoo_Metering_Bar_Meter_Horizontal_bar/blocks/Wide_Range_tribar_demo/demo_02_scale_top
assetsZooMeteringBarMeterHorizontalbarZooMeteringBarMeterHor966f OBJECT-TYPE
    SYNTAX      DisplayString
    MAX-ACCESS  read-write
    STATUS      current
    DESCRIPTION "Source: OPEN-AIR/Assets/Zoo/Metering/Bar_Meter/Horizontal_bar/Zoo_Metering_Bar_Meter_Horizontal_bar/blocks/Wide_Range_tribar_demo/demo_02_scale_top"
    ::= { assetsZooMeteringBarMeterHorizontalbarZooMeteringBarMeterHor6770 33273 }

-- MQTT: OPEN-AIR/Assets/Zoo/Metering/Bar_Meter/Horizontal_bar/Zoo_Metering_Bar_Meter_Horizontal_bar/blocks/Wide_Range_tribar_demo/demo_09_thick_bar_top
assetsZooMeteringBarMeterHorizontalbarZooMeteringBarMeterHora6f9 OBJECT-TYPE
    SYNTAX      DisplayString
    MAX-ACCESS  read-write
    STATUS      current
    DESCRIPTION "Source: OPEN-AIR/Assets/Zoo/Metering/Bar_Meter/Horizontal_bar/Zoo_Metering_Bar_Meter_Horizontal_bar/blocks/Wide_Range_tribar_demo/demo_09_thick_bar_top"
    ::= { assetsZooMeteringBarMeterHorizontalbarZooMeteringBarMeterHor6770 37285 }

-- MQTT: OPEN-AIR/Assets/Zoo/Metering/Bar_Meter/Horizontal_bar/Zoo_Metering_Bar_Meter_Horizontal_bar/blocks/Wide_Range_tribar_demo/demo_01_standard_bottom
assetsZooMeteringBarMeterHorizontalbarZooMeteringBarMeterHorb170 OBJECT-TYPE
    SYNTAX      DisplayString
    MAX-ACCESS  read-write
    STATUS      current
    DESCRIPTION "Source: OPEN-AIR/Assets/Zoo/Metering/Bar_Meter/Horizontal_bar/Zoo_Metering_Bar_Meter_Horizontal_bar/blocks/Wide_Range_tribar_demo/demo_01_standard_bottom"
    ::= { assetsZooMeteringBarMeterHorizontalbarZooMeteringBarMeterHor6770 37397 }

-- MQTT: OPEN-AIR/Assets/Zoo/Metering/Bar_Meter/Horizontal_bar/Zoo_Metering_Bar_Meter_Horizontal_bar/blocks/Wide_Range_tribar_demo/demo_03_no_ticks_bottom_text
assetsZooMeteringBarMeterHorizontalbarZooMeteringBarMeterHor5e53 OBJECT-TYPE
    SYNTAX      DisplayString
    MAX-ACCESS  read-write
    STATUS      current
    DESCRIPTION "Source: OPEN-AIR/Assets/Zoo/Metering/Bar_Meter/Horizontal_bar/Zoo_Metering_Bar_Meter_Horizontal_bar/blocks/Wide_Range_tribar_demo/demo_03_no_ticks_bottom_text"
    ::= { assetsZooMeteringBarMeterHorizontalbarZooMeteringBarMeterHor6770 62821 }

assetsZooMeteringBarMeterHorizontalTric064 OBJECT IDENTIFIER ::= { assetsZooMeteringBarMetera475 2 }
assetsZooMeteringBarMeterHorizontalTriZooMeteringBarMeterHor34d0 OBJECT IDENTIFIER ::= { assetsZooMeteringBarMeterHorizontalTric064 49415 }
assetsZooMeteringBarMeterHorizontalTriZooMeteringBarMeterHor3219 OBJECT IDENTIFIER ::= { assetsZooMeteringBarMeterHorizontalTriZooMeteringBarMeterHor34d0 16864 }
assetsZooMeteringBarMeterHorizontalTriZooMeteringBarMeterHor240a OBJECT IDENTIFIER ::= { assetsZooMeteringBarMeterHorizontalTriZooMeteringBarMeterHor3219 18596 }
-- MQTT: OPEN-AIR/Assets/Zoo/Metering/Bar_Meter/Horizontal_Tri/Zoo_Metering_Bar_Meter_Horizontal_Tri/blocks/Wide_Range_Horizontal/demo_03_no_ticks_bottom_text
assetsZooMeteringBarMeterHorizontalTriZooMeteringBarMeterHor81ed OBJECT-TYPE
    SYNTAX      DisplayString
    MAX-ACCESS  read-write
    STATUS      current
    DESCRIPTION "Source: OPEN-AIR/Assets/Zoo/Metering/Bar_Meter/Horizontal_Tri/Zoo_Metering_Bar_Meter_Horizontal_Tri/blocks/Wide_Range_Horizontal/demo_03_no_ticks_bottom_text"
    ::= { assetsZooMeteringBarMeterHorizontalTriZooMeteringBarMeterHor240a 21877 }

-- MQTT: OPEN-AIR/Assets/Zoo/Metering/Bar_Meter/Horizontal_Tri/Zoo_Metering_Bar_Meter_Horizontal_Tri/blocks/Wide_Range_Horizontal/demo_01_standard_bottom
assetsZooMeteringBarMeterHorizontalTriZooMeteringBarMeterHor3c9d OBJECT-TYPE
    SYNTAX      DisplayString
    MAX-ACCESS  read-write
    STATUS      current
    DESCRIPTION "Source: OPEN-AIR/Assets/Zoo/Metering/Bar_Meter/Horizontal_Tri/Zoo_Metering_Bar_Meter_Horizontal_Tri/blocks/Wide_Range_Horizontal/demo_01_standard_bottom"
    ::= { assetsZooMeteringBarMeterHorizontalTriZooMeteringBarMeterHor240a 30007 }

-- MQTT: OPEN-AIR/Assets/Zoo/Metering/Bar_Meter/Horizontal_Tri/Zoo_Metering_Bar_Meter_Horizontal_Tri/blocks/Wide_Range_Horizontal/demo_06_rect_peak_top
assetsZooMeteringBarMeterHorizontalTriZooMeteringBarMeterHor2f53 OBJECT-TYPE
    SYNTAX      DisplayString
    MAX-ACCESS  read-write
    STATUS      current
    DESCRIPTION "Source: OPEN-AIR/Assets/Zoo/Metering/Bar_Meter/Horizontal_Tri/Zoo_Metering_Bar_Meter_Horizontal_Tri/blocks/Wide_Range_Horizontal/demo_06_rect_peak_top"
    ::= { assetsZooMeteringBarMeterHorizontalTriZooMeteringBarMeterHor240a 30346 }

-- MQTT: OPEN-AIR/Assets/Zoo/Metering/Bar_Meter/Horizontal_Tri/Zoo_Metering_Bar_Meter_Horizontal_Tri/blocks/Wide_Range_Horizontal/demo_02_scale_top
assetsZooMeteringBarMeterHorizontalTriZooMeteringBarMeterHorba24 OBJECT-TYPE
    SYNTAX      DisplayString
    MAX-ACCESS  read-write
    STATUS      current
    DESCRIPTION "Source: OPEN-AIR/Assets/Zoo/Metering/Bar_Meter/Horizontal_Tri/Zoo_Metering_Bar_Meter_Horizontal_Tri/blocks/Wide_Range_Horizontal/demo_02_scale_top"
    ::= { assetsZooMeteringBarMeterHorizontalTriZooMeteringBarMeterHor240a 46856 }

assetsZooMeteringBarMeterVerticalbar6d72 OBJECT IDENTIFIER ::= { assetsZooMeteringBarMetera475 3 }
assetsZooMeteringBarMeterVerticalbarZooMeteringBarMeterVerti6d6d OBJECT IDENTIFIER ::= { assetsZooMeteringBarMeterVerticalbar6d72 47441 }
assetsZooMeteringBarMeterVerticalbarZooMeteringBarMeterVerticb3f OBJECT IDENTIFIER ::= { assetsZooMeteringBarMeterVerticalbarZooMeteringBarMeterVerti6d6d 40524 }
assetsZooMeteringBarMeterVerticalbarZooMeteringBarMeterVertieeb9 OBJECT IDENTIFIER ::= { assetsZooMeteringBarMeterVerticalbarZooMeteringBarMeterVerticb3f 32144 }
-- MQTT: OPEN-AIR/Assets/Zoo/Metering/Bar_Meter/Vertical_bar/Zoo_Metering_Bar_Meter_Vertical_bar/blocks/Wide_Vertical/demo_02_scale_top
assetsZooMeteringBarMeterVerticalbarZooMeteringBarMeterVerti686b OBJECT-TYPE
    SYNTAX      DisplayString
    MAX-ACCESS  read-write
    STATUS      current
    DESCRIPTION "Source: OPEN-AIR/Assets/Zoo/Metering/Bar_Meter/Vertical_bar/Zoo_Metering_Bar_Meter_Vertical_bar/blocks/Wide_Vertical/demo_02_scale_top"
    ::= { assetsZooMeteringBarMeterVerticalbarZooMeteringBarMeterVertieeb9 10520 }

-- MQTT: OPEN-AIR/Assets/Zoo/Metering/Bar_Meter/Vertical_bar/Zoo_Metering_Bar_Meter_Vertical_bar/blocks/Wide_Vertical/demo_03_no_ticks_bottom_text
assetsZooMeteringBarMeterVerticalbarZooMeteringBarMeterVertib56a OBJECT-TYPE
    SYNTAX      DisplayString
    MAX-ACCESS  read-write
    STATUS      current
    DESCRIPTION "Source: OPEN-AIR/Assets/Zoo/Metering/Bar_Meter/Vertical_bar/Zoo_Metering_Bar_Meter_Vertical_bar/blocks/Wide_Vertical/demo_03_no_ticks_bottom_text"
    ::= { assetsZooMeteringBarMeterVerticalbarZooMeteringBarMeterVertieeb9 37971 }

assetsZooCompositec419 OBJECT IDENTIFIER ::= { assetsZoo5f4e 3 }
assetsZooCompositeControlElements5804 OBJECT IDENTIFIER ::= { assetsZooCompositec419 0 }
assetsZooCompositeControlElementsZoocompositeControlElementsf258 OBJECT IDENTIFIER ::= { assetsZooCompositeControlElements5804 8859 }
assetsZooCompositeControlElementsZoocompositeControlElements5811 OBJECT IDENTIFIER ::= { assetsZooCompositeControlElementsZoocompositeControlElementsf258 32269 }
assetsZooCompositeControlElementsZoocompositeControlElements462e OBJECT IDENTIFIER ::= { assetsZooCompositeControlElementsZoocompositeControlElements5811 32461 }
-- MQTT: OPEN-AIR/Assets/Zoo/composite/Control_Elements/Zoo_composite_Control_Elements/blocks/tutorial_intro/desc_main
assetsZooCompositeControlElementsZoocompositeControlElementscd90 OBJECT-TYPE
    SYNTAX      DisplayString
    MAX-ACCESS  read-write
    STATUS      current
    DESCRIPTION "Source: OPEN-AIR/Assets/Zoo/composite/Control_Elements/Zoo_composite_Control_Elements/blocks/tutorial_intro/desc_main"
    ::= { assetsZooCompositeControlElementsZoocompositeControlElements462e 7693 }

assetsZooCompositeControlElementsZoocompositeControlElements4781 OBJECT IDENTIFIER ::= { assetsZooCompositeControlElementsZoocompositeControlElements5811 43371 }
-- MQTT: OPEN-AIR/Assets/Zoo/composite/Control_Elements/Zoo_composite_Control_Elements/blocks/Standard_Gui_Elements/w04
assetsZooCompositeControlElementsZoocompositeControlElements86f7 OBJECT-TYPE
    SYNTAX      DisplayString
    MAX-ACCESS  read-write
    STATUS      current
    DESCRIPTION "Source: OPEN-AIR/Assets/Zoo/composite/Control_Elements/Zoo_composite_Control_Elements/blocks/Standard_Gui_Elements/w04"
    ::= { assetsZooCompositeControlElementsZoocompositeControlElements4781 46899 }

assetsZooGraphingc5f4 OBJECT IDENTIFIER ::= { assetsZoo5f4e 4 }
assetsZooGraphingRadar475c OBJECT IDENTIFIER ::= { assetsZooGraphingc5f4 0 }
assetsZooGraphingRadarSamplec916 OBJECT IDENTIFIER ::= { assetsZooGraphingRadar475c 1 }
assetsZooGraphingRadarSampleZoodatagraphingradarSample1d63e OBJECT IDENTIFIER ::= { assetsZooGraphingRadarSamplec916 14758 }
assetsZooGraphingRadarSampleZoodatagraphingradarSample1Blockc196 OBJECT IDENTIFIER ::= { assetsZooGraphingRadarSampleZoodatagraphingradarSample1d63e 62019 }
assetsZooGraphingRadarSampleZoodatagraphingradarSample1Block5aa1 OBJECT IDENTIFIER ::= { assetsZooGraphingRadarSampleZoodatagraphingradarSample1Blockc196 2199 }
-- MQTT: OPEN-AIR/Assets/Zoo/graphing/radar/Sample/Zoo_data_graphing_radar_Sample_1/blocks/Radar_Eye_Zoo/radar_eye_2
assetsZooGraphingRadarSampleZoodatagraphingradarSample1Blocked95 OBJECT-TYPE
    SYNTAX      DisplayString
    MAX-ACCESS  read-write
    STATUS      current
    DESCRIPTION "Source: OPEN-AIR/Assets/Zoo/graphing/radar/Sample/Zoo_data_graphing_radar_Sample_1/blocks/Radar_Eye_Zoo/radar_eye_2"
    ::= { assetsZooGraphingRadarSampleZoodatagraphingradarSample1Block5aa1 8989 }

-- MQTT: OPEN-AIR/Assets/Zoo/graphing/radar/Sample/Zoo_data_graphing_radar_Sample_1/blocks/Radar_Eye_Zoo/radar_eye_1
assetsZooGraphingRadarSampleZoodatagraphingradarSample1Block749c OBJECT-TYPE
    SYNTAX      DisplayString
    MAX-ACCESS  read-write
    STATUS      current
    DESCRIPTION "Source: OPEN-AIR/Assets/Zoo/graphing/radar/Sample/Zoo_data_graphing_radar_Sample_1/blocks/Radar_Eye_Zoo/radar_eye_1"
    ::= { assetsZooGraphingRadarSampleZoodatagraphingradarSample1Block5aa1 29351 }

-- MQTT: OPEN-AIR/Assets/Zoo/graphing/radar/Sample/Zoo_data_graphing_radar_Sample_1/blocks/Radar_Eye_Zoo/radar_eye_5
assetsZooGraphingRadarSampleZoodatagraphingradarSample1Block73f1 OBJECT-TYPE
    SYNTAX      DisplayString
    MAX-ACCESS  read-write
    STATUS      current
    DESCRIPTION "Source: OPEN-AIR/Assets/Zoo/graphing/radar/Sample/Zoo_data_graphing_radar_Sample_1/blocks/Radar_Eye_Zoo/radar_eye_5"
    ::= { assetsZooGraphingRadarSampleZoodatagraphingradarSample1Block5aa1 46782 }

-- MQTT: OPEN-AIR/Assets/Zoo/graphing/radar/Sample/Zoo_data_graphing_radar_Sample_1/blocks/Radar_Eye_Zoo/radar_eye_9
assetsZooGraphingRadarSampleZoodatagraphingradarSample1Block7a47 OBJECT-TYPE
    SYNTAX      DisplayString
    MAX-ACCESS  read-write
    STATUS      current
    DESCRIPTION "Source: OPEN-AIR/Assets/Zoo/graphing/radar/Sample/Zoo_data_graphing_radar_Sample_1/blocks/Radar_Eye_Zoo/radar_eye_9"
    ::= { assetsZooGraphingRadarSampleZoodatagraphingradarSample1Block5aa1 64149 }

assetsZooGraphingRadarSampleZoodatagraphingradarSamplee7f0 OBJECT IDENTIFIER ::= { assetsZooGraphingRadarSamplec916 16055 }
assetsZooGraphingRadarSampleZoodatagraphingradarSampleBlocks3889 OBJECT IDENTIFIER ::= { assetsZooGraphingRadarSampleZoodatagraphingradarSamplee7f0 40191 }
assetsZooGraphingRadarSampleZoodatagraphingradarSampleBlocks68e7 OBJECT IDENTIFIER ::= { assetsZooGraphingRadarSampleZoodatagraphingradarSampleBlocks3889 54082 }
-- MQTT: OPEN-AIR/Assets/Zoo/graphing/radar/Sample/Zoo_data_graphing_radar_Sample_/blocks/Radar_Eye_Zoo_1/radar_eye_1
assetsZooGraphingRadarSampleZoodatagraphingradarSampleBlocksf9ec OBJECT-TYPE
    SYNTAX      DisplayString
    MAX-ACCESS  read-write
    STATUS      current
    DESCRIPTION "Source: OPEN-AIR/Assets/Zoo/graphing/radar/Sample/Zoo_data_graphing_radar_Sample_/blocks/Radar_Eye_Zoo_1/radar_eye_1"
    ::= { assetsZooGraphingRadarSampleZoodatagraphingradarSampleBlocks68e7 49175 }

assetsZooGraphingRadarSampleZoodatagraphingradarSample33830 OBJECT IDENTIFIER ::= { assetsZooGraphingRadarSamplec916 22666 }
assetsZooGraphingRadarSampleZoodatagraphingradarSample3Block83b3 OBJECT IDENTIFIER ::= { assetsZooGraphingRadarSampleZoodatagraphingradarSample33830 62782 }
assetsZooGraphingRadarSampleZoodatagraphingradarSample3Block2aca OBJECT IDENTIFIER ::= { assetsZooGraphingRadarSampleZoodatagraphingradarSample3Block83b3 12339 }
-- MQTT: OPEN-AIR/Assets/Zoo/graphing/radar/Sample/Zoo_data_graphing_radar_Sample_3/blocks/Radar_Eye_Zoo_3/radar_eye_3
assetsZooGraphingRadarSampleZoodatagraphingradarSample3Blockaa6f OBJECT-TYPE
    SYNTAX      DisplayString
    MAX-ACCESS  read-write
    STATUS      current
    DESCRIPTION "Source: OPEN-AIR/Assets/Zoo/graphing/radar/Sample/Zoo_data_graphing_radar_Sample_3/blocks/Radar_Eye_Zoo_3/radar_eye_3"
    ::= { assetsZooGraphingRadarSampleZoodatagraphingradarSample3Block2aca 2791 }

assetsZooGraphingRadarSampleZoodatagraphingradarSample24f37 OBJECT IDENTIFIER ::= { assetsZooGraphingRadarSamplec916 26652 }
assetsZooGraphingRadarSampleZoodatagraphingradarSample2Block4f19 OBJECT IDENTIFIER ::= { assetsZooGraphingRadarSampleZoodatagraphingradarSample24f37 62880 }
assetsZooGraphingRadarSampleZoodatagraphingradarSample2Blockdce8 OBJECT IDENTIFIER ::= { assetsZooGraphingRadarSampleZoodatagraphingradarSample2Block4f19 25986 }
-- MQTT: OPEN-AIR/Assets/Zoo/graphing/radar/Sample/Zoo_data_graphing_radar_Sample_2/blocks/Radar_Eye_Zoo_2/radar_eye_2
assetsZooGraphingRadarSampleZoodatagraphingradarSample2Block958e OBJECT-TYPE
    SYNTAX      DisplayString
    MAX-ACCESS  read-write
    STATUS      current
    DESCRIPTION "Source: OPEN-AIR/Assets/Zoo/graphing/radar/Sample/Zoo_data_graphing_radar_Sample_2/blocks/Radar_Eye_Zoo_2/radar_eye_2"
    ::= { assetsZooGraphingRadarSampleZoodatagraphingradarSample2Blockdce8 14177 }

-- MQTT: OPEN-AIR/Assets/Zoo/graphing/radar/Sample/Zoo_data_graphing_radar_Sample_2/blocks/Radar_Eye_Zoo_2/radar_eye_1
assetsZooGraphingRadarSampleZoodatagraphingradarSample2Blockc876 OBJECT-TYPE
    SYNTAX      DisplayString
    MAX-ACCESS  read-write
    STATUS      current
    DESCRIPTION "Source: OPEN-AIR/Assets/Zoo/graphing/radar/Sample/Zoo_data_graphing_radar_Sample_2/blocks/Radar_Eye_Zoo_2/radar_eye_1"
    ::= { assetsZooGraphingRadarSampleZoodatagraphingradarSample2Blockdce8 26331 }

assetsZooGraphingRadarSampleZoodatagraphingradarSample4a654 OBJECT IDENTIFIER ::= { assetsZooGraphingRadarSamplec916 52521 }
assetsZooGraphingRadarSampleZoodatagraphingradarSample4Block8976 OBJECT IDENTIFIER ::= { assetsZooGraphingRadarSampleZoodatagraphingradarSample4a654 64551 }
assetsZooGraphingRadarSampleZoodatagraphingradarSample4Block85b6 OBJECT IDENTIFIER ::= { assetsZooGraphingRadarSampleZoodatagraphingradarSample4Block8976 37607 }
-- MQTT: OPEN-AIR/Assets/Zoo/graphing/radar/Sample/Zoo_data_graphing_radar_Sample_4/blocks/Radar_Eye_Zoo_4/radar_01
assetsZooGraphingRadarSampleZoodatagraphingradarSample4Block59a6 OBJECT-TYPE
    SYNTAX      DisplayString
    MAX-ACCESS  read-write
    STATUS      current
    DESCRIPTION "Source: OPEN-AIR/Assets/Zoo/graphing/radar/Sample/Zoo_data_graphing_radar_Sample_4/blocks/Radar_Eye_Zoo_4/radar_01"
    ::= { assetsZooGraphingRadarSampleZoodatagraphingradarSample4Block85b6 3293 }

-- MQTT: OPEN-AIR/Assets/Zoo/graphing/radar/Sample/Zoo_data_graphing_radar_Sample_4/blocks/Radar_Eye_Zoo_4/radar_11
assetsZooGraphingRadarSampleZoodatagraphingradarSample4Block40bd OBJECT-TYPE
    SYNTAX      DisplayString
    MAX-ACCESS  read-write
    STATUS      current
    DESCRIPTION "Source: OPEN-AIR/Assets/Zoo/graphing/radar/Sample/Zoo_data_graphing_radar_Sample_4/blocks/Radar_Eye_Zoo_4/radar_11"
    ::= { assetsZooGraphingRadarSampleZoodatagraphingradarSample4Block85b6 15772 }

-- MQTT: OPEN-AIR/Assets/Zoo/graphing/radar/Sample/Zoo_data_graphing_radar_Sample_4/blocks/Radar_Eye_Zoo_4/radar_02
assetsZooGraphingRadarSampleZoodatagraphingradarSample4Blockc0af OBJECT-TYPE
    SYNTAX      DisplayString
    MAX-ACCESS  read-write
    STATUS      current
    DESCRIPTION "Source: OPEN-AIR/Assets/Zoo/graphing/radar/Sample/Zoo_data_graphing_radar_Sample_4/blocks/Radar_Eye_Zoo_4/radar_02"
    ::= { assetsZooGraphingRadarSampleZoodatagraphingradarSample4Block85b6 23911 }

assetsZooGraphingXYGraphsa6ac OBJECT IDENTIFIER ::= { assetsZooGraphingc5f4 1 }
assetsZooGraphingXYGraphsGraphingf0fa OBJECT IDENTIFIER ::= { assetsZooGraphingXYGraphsa6ac 2 }
assetsZooGraphingXYGraphsGraphingZoodatagraphingXYGraphsGrapf371 OBJECT IDENTIFIER ::= { assetsZooGraphingXYGraphsGraphingf0fa 49733 }
assetsZooGraphingXYGraphsGraphingZoodatagraphingXYGraphsGrapc1c4 OBJECT IDENTIFIER ::= { assetsZooGraphingXYGraphsGraphingZoodatagraphingXYGraphsGrapf371 14215 }
assetsZooGraphingXYGraphsGraphingZoodatagraphingXYGraphsGrap3b95 OBJECT IDENTIFIER ::= { assetsZooGraphingXYGraphsGraphingZoodatagraphingXYGraphsGrapc1c4 6188 }
assetsZooGraphingXYGraphsGraphingZoodatagraphingXYGraphsGrapbcb8 OBJECT IDENTIFIER ::= { assetsZooGraphingXYGraphsGraphingZoodatagraphingXYGraphsGrap3b95 30415 }
-- MQTT: OPEN-AIR/Assets/Zoo/graphing/XY_Graphs/Graphing/Zoo_data_graphing_XY_Graphs_Graphing_3/blocks/Scatter_Plot/oaDataRunningFiles/scatter_data
assetsZooGraphingXYGraphsGraphingZoodatagraphingXYGraphsGrap931a OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Scatter_Plot/oaDataRunningFiles/scatter_data"
    ::= { assetsZooGraphingXYGraphsGraphingZoodatagraphingXYGraphsGrapbcb8 4995 }

assetsZooGraphingXYGraphsGraphingZoodatagraphingXYGraphsGrapbe82 OBJECT IDENTIFIER ::= { assetsZooGraphingXYGraphsGraphingZoodatagraphingXYGraphsGrapc1c4 24129 }
assetsZooGraphingXYGraphsGraphingZoodatagraphingXYGraphsGrap8d2a OBJECT IDENTIFIER ::= { assetsZooGraphingXYGraphsGraphingZoodatagraphingXYGraphsGrapbe82 22814 }
-- MQTT: OPEN-AIR/Assets/Zoo/graphing/XY_Graphs/Graphing/Zoo_data_graphing_XY_Graphs_Graphing_3/blocks/Log_Y_Zoom/settings/title
assetsZooGraphingXYGraphsGraphingZoodatagraphingXYGraphsGrap8091 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Log_Y_Zoom/settings/title"
    ::= { assetsZooGraphingXYGraphsGraphingZoodatagraphingXYGraphsGrap8d2a 37102 }

assetsZooGraphingXYGraphsGraphingZoodatagraphingXYGraphsGrap4589 OBJECT IDENTIFIER ::= { assetsZooGraphingXYGraphsGraphingZoodatagraphingXYGraphsGrapbe82 26109 }
-- MQTT: OPEN-AIR/Assets/Zoo/graphing/XY_Graphs/Graphing/Zoo_data_graphing_XY_Graphs_Graphing_3/blocks/Log_Y_Zoom/oaDataRunningFiles/exp_growth
assetsZooGraphingXYGraphsGraphingZoodatagraphingXYGraphsGrap9abb OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Log_Y_Zoom/oaDataRunningFiles/exp_growth"
    ::= { assetsZooGraphingXYGraphsGraphingZoodatagraphingXYGraphsGrap4589 45917 }

assetsZooGraphingXYGraphsGraphingZoodatagraphingXYGraphsGrap22e1 OBJECT IDENTIFIER ::= { assetsZooGraphingXYGraphsGraphingZoodatagraphingXYGraphsGrapc1c4 29505 }
assetsZooGraphingXYGraphsGraphingZoodatagraphingXYGraphsGrapd6e3 OBJECT IDENTIFIER ::= { assetsZooGraphingXYGraphsGraphingZoodatagraphingXYGraphsGrap22e1 7694 }
-- MQTT: OPEN-AIR/Assets/Zoo/graphing/XY_Graphs/Graphing/Zoo_data_graphing_XY_Graphs_Graphing_3/blocks/Spiral_Plot/oaDataRunningFiles/spiral
assetsZooGraphingXYGraphsGraphingZoodatagraphingXYGraphsGrapfcec OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Spiral_Plot/oaDataRunningFiles/spiral"
    ::= { assetsZooGraphingXYGraphsGraphingZoodatagraphingXYGraphsGrapd6e3 14709 }

-- MQTT: OPEN-AIR/Assets/Zoo/graphing/XY_Graphs/Graphing/Zoo_data_graphing_XY_Graphs_Graphing_3/blocks/Spiral_Plot/oaDataRunningFiles/MARKERS
assetsZooGraphingXYGraphsGraphingZoodatagraphingXYGraphsGrap2d9f OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Spiral_Plot/oaDataRunningFiles/MARKERS"
    ::= { assetsZooGraphingXYGraphsGraphingZoodatagraphingXYGraphsGrapd6e3 47529 }

assetsZooGraphingXYGraphsGraphingZoodatagraphingXYGraphsGrap3fa3 OBJECT IDENTIFIER ::= { assetsZooGraphingXYGraphsGraphingZoodatagraphingXYGraphsGrap22e1 44761 }
-- MQTT: OPEN-AIR/Assets/Zoo/graphing/XY_Graphs/Graphing/Zoo_data_graphing_XY_Graphs_Graphing_3/blocks/Spiral_Plot/settings/ylim
assetsZooGraphingXYGraphsGraphingZoodatagraphingXYGraphsGrapffc4 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Spiral_Plot/settings/ylim"
    ::= { assetsZooGraphingXYGraphsGraphingZoodatagraphingXYGraphsGrap3fa3 58762 }

assetsZooGraphingXYGraphsGraphingZoodatagraphingXYGraphsGrap131c OBJECT IDENTIFIER ::= { assetsZooGraphingXYGraphsGraphingZoodatagraphingXYGraphsGrapc1c4 33882 }
assetsZooGraphingXYGraphsGraphingZoodatagraphingXYGraphsGrap7a8d OBJECT IDENTIFIER ::= { assetsZooGraphingXYGraphsGraphingZoodatagraphingXYGraphsGrap131c 46206 }
-- MQTT: OPEN-AIR/Assets/Zoo/graphing/XY_Graphs/Graphing/Zoo_data_graphing_XY_Graphs_Graphing_3/blocks/Log_Log_Zoom/oaDataRunningFiles/power_law
assetsZooGraphingXYGraphsGraphingZoodatagraphingXYGraphsGrap4b5a OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Log_Log_Zoom/oaDataRunningFiles/power_law"
    ::= { assetsZooGraphingXYGraphsGraphingZoodatagraphingXYGraphsGrap7a8d 10775 }

assetsZooGraphingXYGraphsGraphingZoodatagraphingXYGraphsGrap75de OBJECT IDENTIFIER ::= { assetsZooGraphingXYGraphsGraphingZoodatagraphingXYGraphsGrapc1c4 36324 }
assetsZooGraphingXYGraphsGraphingZoodatagraphingXYGraphsGrape002 OBJECT IDENTIFIER ::= { assetsZooGraphingXYGraphsGraphingZoodatagraphingXYGraphsGrap75de 62963 }
-- MQTT: OPEN-AIR/Assets/Zoo/graphing/XY_Graphs/Graphing/Zoo_data_graphing_XY_Graphs_Graphing_3/blocks/Log_X_Zoom/oaDataRunningFiles/log_decay
assetsZooGraphingXYGraphsGraphingZoodatagraphingXYGraphsGrap44f2 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Log_X_Zoom/oaDataRunningFiles/log_decay"
    ::= { assetsZooGraphingXYGraphsGraphingZoodatagraphingXYGraphsGrape002 6235 }

assetsZooGraphingXYGraphsGraphingZoodatagraphingXYGraphsGrap5341 OBJECT IDENTIFIER ::= { assetsZooGraphingXYGraphsGraphingZoodatagraphingXYGraphsGrapc1c4 43005 }
assetsZooGraphingXYGraphsGraphingZoodatagraphingXYGraphsGrap4d31 OBJECT IDENTIFIER ::= { assetsZooGraphingXYGraphsGraphingZoodatagraphingXYGraphsGrap5341 23874 }
-- MQTT: OPEN-AIR/Assets/Zoo/graphing/XY_Graphs/Graphing/Zoo_data_graphing_XY_Graphs_Graphing_3/blocks/Multi_Style_Plot/oaDataRunningFiles/data2
assetsZooGraphingXYGraphsGraphingZoodatagraphingXYGraphsGrapfd1f OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Multi_Style_Plot/oaDataRunningFiles/data2"
    ::= { assetsZooGraphingXYGraphsGraphingZoodatagraphingXYGraphsGrap4d31 48395 }

-- MQTT: OPEN-AIR/Assets/Zoo/graphing/XY_Graphs/Graphing/Zoo_data_graphing_XY_Graphs_Graphing_3/blocks/Multi_Style_Plot/oaDataRunningFiles/data1
assetsZooGraphingXYGraphsGraphingZoodatagraphingXYGraphsGrap6416 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Multi_Style_Plot/oaDataRunningFiles/data1"
    ::= { assetsZooGraphingXYGraphsGraphingZoodatagraphingXYGraphsGrap4d31 60593 }

assetsZooGraphingXYGraphsGraphingZoodatagraphingXYGraphsGrap9471 OBJECT IDENTIFIER ::= { assetsZooGraphingXYGraphsGraphingZoodatagraphingXYGraphsGrap5341 59580 }
-- MQTT: OPEN-AIR/Assets/Zoo/graphing/XY_Graphs/Graphing/Zoo_data_graphing_XY_Graphs_Graphing_3/blocks/Multi_Style_Plot/settings/title
assetsZooGraphingXYGraphsGraphingZoodatagraphingXYGraphsGrapf619 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Multi_Style_Plot/settings/title"
    ::= { assetsZooGraphingXYGraphsGraphingZoodatagraphingXYGraphsGrap9471 4595 }

assetsZooGraphingXYGraphsGraphingZoodatagraphingXYGraphsGrap324f OBJECT IDENTIFIER ::= { assetsZooGraphingXYGraphsGraphingZoodatagraphingXYGraphsGrapc1c4 46197 }
assetsZooGraphingXYGraphsGraphingZoodatagraphingXYGraphsGrap285f OBJECT IDENTIFIER ::= { assetsZooGraphingXYGraphsGraphingZoodatagraphingXYGraphsGrap324f 56193 }
-- MQTT: OPEN-AIR/Assets/Zoo/graphing/XY_Graphs/Graphing/Zoo_data_graphing_XY_Graphs_Graphing_3/blocks/Heartbeat_Plot/settings/title
assetsZooGraphingXYGraphsGraphingZoodatagraphingXYGraphsGrap24d5 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Heartbeat_Plot/settings/title"
    ::= { assetsZooGraphingXYGraphsGraphingZoodatagraphingXYGraphsGrap285f 6319 }

assetsZooGraphingXYGraphsGraphingZoodatagraphingXYGraphsGrapcca9 OBJECT IDENTIFIER ::= { assetsZooGraphingXYGraphsGraphingZoodatagraphingXYGraphsGrap324f 64877 }
-- MQTT: OPEN-AIR/Assets/Zoo/graphing/XY_Graphs/Graphing/Zoo_data_graphing_XY_Graphs_Graphing_3/blocks/Heartbeat_Plot/oaDataRunningFiles/ekg
assetsZooGraphingXYGraphsGraphingZoodatagraphingXYGraphsGrap5b91 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Heartbeat_Plot/oaDataRunningFiles/ekg"
    ::= { assetsZooGraphingXYGraphsGraphingZoodatagraphingXYGraphsGrapcca9 26958 }

assetsZooGraphingXYGraphsGraphingZoodatagraphingXYGraphsGrape867 OBJECT IDENTIFIER ::= { assetsZooGraphingXYGraphsGraphingZoodatagraphingXYGraphsGrapc1c4 48562 }
assetsZooGraphingXYGraphsGraphingZoodatagraphingXYGraphsGrap129b OBJECT IDENTIFIER ::= { assetsZooGraphingXYGraphsGraphingZoodatagraphingXYGraphsGrape867 47211 }
-- MQTT: OPEN-AIR/Assets/Zoo/graphing/XY_Graphs/Graphing/Zoo_data_graphing_XY_Graphs_Graphing_3/blocks/Scientific_Plot/oaDataRunningFiles/scientific_data
assetsZooGraphingXYGraphsGraphingZoodatagraphingXYGraphsGrap860d OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Scientific_Plot/oaDataRunningFiles/scientific_data"
    ::= { assetsZooGraphingXYGraphsGraphingZoodatagraphingXYGraphsGrap129b 58857 }

assetsZooGraphingXYGraphsGraphingZoodatagraphingXYGraphsGrapa441 OBJECT IDENTIFIER ::= { assetsZooGraphingXYGraphsGraphingZoodatagraphingXYGraphsGrape867 59033 }
-- MQTT: OPEN-AIR/Assets/Zoo/graphing/XY_Graphs/Graphing/Zoo_data_graphing_XY_Graphs_Graphing_3/blocks/Scientific_Plot/settings/xlim
assetsZooGraphingXYGraphsGraphingZoodatagraphingXYGraphsGrap79f8 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Scientific_Plot/settings/xlim"
    ::= { assetsZooGraphingXYGraphsGraphingZoodatagraphingXYGraphsGrapa441 64875 }

assetsZooGraphingXYGraphsGraphingZoodatagraphingXYGraphsGrap489c OBJECT IDENTIFIER ::= { assetsZooGraphingXYGraphsGraphingZoodatagraphingXYGraphsGrapc1c4 51361 }
assetsZooGraphingXYGraphsGraphingZoodatagraphingXYGraphsGrapbcdf OBJECT IDENTIFIER ::= { assetsZooGraphingXYGraphsGraphingZoodatagraphingXYGraphsGrap489c 30575 }
-- MQTT: OPEN-AIR/Assets/Zoo/graphing/XY_Graphs/Graphing/Zoo_data_graphing_XY_Graphs_Graphing_3/blocks/All_Features_Plot/oaDataRunningFiles/noise
assetsZooGraphingXYGraphsGraphingZoodatagraphingXYGraphsGrap7c90 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/All_Features_Plot/oaDataRunningFiles/noise"
    ::= { assetsZooGraphingXYGraphsGraphingZoodatagraphingXYGraphsGrapbcdf 22687 }

-- MQTT: OPEN-AIR/Assets/Zoo/graphing/XY_Graphs/Graphing/Zoo_data_graphing_XY_Graphs_Graphing_3/blocks/All_Features_Plot/oaDataRunningFiles/signal
assetsZooGraphingXYGraphsGraphingZoodatagraphingXYGraphsGrap568f OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/All_Features_Plot/oaDataRunningFiles/signal"
    ::= { assetsZooGraphingXYGraphsGraphingZoodatagraphingXYGraphsGrapbcdf 47746 }

assetsZooGraphingXYGraphsGraphingZoodatagraphingXYGraphsGrapaad9 OBJECT IDENTIFIER ::= { assetsZooGraphingXYGraphsGraphingZoodatagraphingXYGraphsGrap489c 30740 }
-- MQTT: OPEN-AIR/Assets/Zoo/graphing/XY_Graphs/Graphing/Zoo_data_graphing_XY_Graphs_Graphing_3/blocks/All_Features_Plot/settings/x_label
assetsZooGraphingXYGraphsGraphingZoodatagraphingXYGraphsGrap877e OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/All_Features_Plot/settings/x_label"
    ::= { assetsZooGraphingXYGraphsGraphingZoodatagraphingXYGraphsGrapaad9 18245 }

-- MQTT: OPEN-AIR/Assets/Zoo/graphing/XY_Graphs/Graphing/Zoo_data_graphing_XY_Graphs_Graphing_3/blocks/All_Features_Plot/settings/y_label
assetsZooGraphingXYGraphsGraphingZoodatagraphingXYGraphsGrap2109 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/All_Features_Plot/settings/y_label"
    ::= { assetsZooGraphingXYGraphsGraphingZoodatagraphingXYGraphsGrapaad9 19697 }

-- MQTT: OPEN-AIR/Assets/Zoo/graphing/XY_Graphs/Graphing/Zoo_data_graphing_XY_Graphs_Graphing_3/blocks/All_Features_Plot/settings/show_grid
assetsZooGraphingXYGraphsGraphingZoodatagraphingXYGraphsGrapd6b5 OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/All_Features_Plot/settings/show_grid"
    ::= { assetsZooGraphingXYGraphsGraphingZoodatagraphingXYGraphsGrapaad9 35385 }

assetsZooGraphingXYGraphsGraphingZoodatagraphingXYGraphsGrapb933 OBJECT IDENTIFIER ::= { assetsZooGraphingXYGraphsGraphingZoodatagraphingXYGraphsGrapc1c4 62830 }
assetsZooGraphingXYGraphsGraphingZoodatagraphingXYGraphsGrapbc42 OBJECT IDENTIFIER ::= { assetsZooGraphingXYGraphsGraphingZoodatagraphingXYGraphsGrapb933 39706 }
-- MQTT: OPEN-AIR/Assets/Zoo/graphing/XY_Graphs/Graphing/Zoo_data_graphing_XY_Graphs_Graphing_3/blocks/Financial_Plot/settings/x_label
assetsZooGraphingXYGraphsGraphingZoodatagraphingXYGraphsGrap38bd OBJECT-TYPE
    SYNTAX      DisplayString
    MAX-ACCESS  read-write
    STATUS      current
    DESCRIPTION "Source: OPEN-AIR/Assets/Zoo/graphing/XY_Graphs/Graphing/Zoo_data_graphing_XY_Graphs_Graphing_3/blocks/Financial_Plot/settings/x_label"
    ::= { assetsZooGraphingXYGraphsGraphingZoodatagraphingXYGraphsGrapbc42 27999 }

assetsZooGraphingXYGraphsGraphingBlocks3c1c OBJECT IDENTIFIER ::= { assetsZooGraphingXYGraphsGraphingf0fa 52000 }
assetsZooGraphingXYGraphsGraphingBlocksOceanPlot73c2 OBJECT IDENTIFIER ::= { assetsZooGraphingXYGraphsGraphingBlocks3c1c 10908 }
assetsZooGraphingXYGraphsGraphingBlocksOceanPlotSettingsdf71 OBJECT IDENTIFIER ::= { assetsZooGraphingXYGraphsGraphingBlocksOceanPlot73c2 5722 }
-- MQTT: OPEN-AIR/Assets/Zoo/graphing/XY_Graphs/Graphing/blocks/Ocean_Plot/settings/show_grid
assetsZooGraphingXYGraphsGraphingBlocksOceanPlotSettingsShowac97 OBJECT-TYPE
    SYNTAX      DisplayString
    MAX-ACCESS  read-write
    STATUS      current
    DESCRIPTION "Source: OPEN-AIR/Assets/Zoo/graphing/XY_Graphs/Graphing/blocks/Ocean_Plot/settings/show_grid"
    ::= { assetsZooGraphingXYGraphsGraphingBlocksOceanPlotSettingsdf71 31384 }

assetsZooGraphingXYGraphsGraphingBlocksOceanPlotOaDataRunninc6fd OBJECT IDENTIFIER ::= { assetsZooGraphingXYGraphsGraphingBlocksOceanPlot73c2 34766 }
-- MQTT: OPEN-AIR/Assets/Zoo/graphing/XY_Graphs/Graphing/blocks/Ocean_Plot/oaDataRunningFiles/wave1
assetsZooGraphingXYGraphsGraphingBlocksOceanPlotOaDataRunnin5f72 OBJECT-TYPE
    SYNTAX      DisplayString
    MAX-ACCESS  read-write
    STATUS      current
    DESCRIPTION "Source: OPEN-AIR/Assets/Zoo/graphing/XY_Graphs/Graphing/blocks/Ocean_Plot/oaDataRunningFiles/wave1"
    ::= { assetsZooGraphingXYGraphsGraphingBlocksOceanPlotOaDataRunninc6fd 1549 }

assetsZooGraphingXYGraphsGraphingBlocksSunsetPlotd301 OBJECT IDENTIFIER ::= { assetsZooGraphingXYGraphsGraphingBlocks3c1c 13051 }
assetsZooGraphingXYGraphsGraphingBlocksSunsetPlotOaDataRunnib564 OBJECT IDENTIFIER ::= { assetsZooGraphingXYGraphsGraphingBlocksSunsetPlotd301 1327 }
-- MQTT: OPEN-AIR/Assets/Zoo/graphing/XY_Graphs/Graphing/blocks/Sunset_Plot/oaDataRunningFiles/hill2
assetsZooGraphingXYGraphsGraphingBlocksSunsetPlotOaDataRunnia1cd OBJECT-TYPE
    SYNTAX      DisplayString
    MAX-ACCESS  read-write
    STATUS      current
    DESCRIPTION "Source: OPEN-AIR/Assets/Zoo/graphing/XY_Graphs/Graphing/blocks/Sunset_Plot/oaDataRunningFiles/hill2"
    ::= { assetsZooGraphingXYGraphsGraphingBlocksSunsetPlotOaDataRunnib564 45334 }

-- MQTT: OPEN-AIR/Assets/Zoo/graphing/XY_Graphs/Graphing/blocks/Sunset_Plot/oaDataRunningFiles/hill1
assetsZooGraphingXYGraphsGraphingBlocksSunsetPlotOaDataRunni38c4 OBJECT-TYPE
    SYNTAX      DisplayString
    MAX-ACCESS  read-write
    STATUS      current
    DESCRIPTION "Source: OPEN-AIR/Assets/Zoo/graphing/XY_Graphs/Graphing/blocks/Sunset_Plot/oaDataRunningFiles/hill1"
    ::= { assetsZooGraphingXYGraphsGraphingBlocksSunsetPlotOaDataRunnib564 57516 }

assetsZooGraphingXYGraphsGraphingBlocksSunsetPlotSettingsdab0 OBJECT IDENTIFIER ::= { assetsZooGraphingXYGraphsGraphingBlocksSunsetPlotd301 18946 }
-- MQTT: OPEN-AIR/Assets/Zoo/graphing/XY_Graphs/Graphing/blocks/Sunset_Plot/settings/y_label
assetsZooGraphingXYGraphsGraphingBlocksSunsetPlotSettingsYla7208 OBJECT-TYPE
    SYNTAX      DisplayString
    MAX-ACCESS  read-write
    STATUS      current
    DESCRIPTION "Source: OPEN-AIR/Assets/Zoo/graphing/XY_Graphs/Graphing/blocks/Sunset_Plot/settings/y_label"
    ::= { assetsZooGraphingXYGraphsGraphingBlocksSunsetPlotSettingsdab0 32379 }

assetsZooGraphingXYGraphsGraphingBlocksBlueprintPlotdc99 OBJECT IDENTIFIER ::= { assetsZooGraphingXYGraphsGraphingBlocks3c1c 50724 }
assetsZooGraphingXYGraphsGraphingBlocksBlueprintPlotOaDataRu9b2c OBJECT IDENTIFIER ::= { assetsZooGraphingXYGraphsGraphingBlocksBlueprintPlotdc99 17261 }
-- MQTT: OPEN-AIR/Assets/Zoo/graphing/XY_Graphs/Graphing/blocks/Blueprint_Plot/oaDataRunningFiles/blueprint_line
assetsZooGraphingXYGraphsGraphingBlocksBlueprintPlotOaDataRu3efe OBJECT-TYPE
    SYNTAX      DisplayString
    MAX-ACCESS  read-write
    STATUS      current
    DESCRIPTION "Source: OPEN-AIR/Assets/Zoo/graphing/XY_Graphs/Graphing/blocks/Blueprint_Plot/oaDataRunningFiles/blueprint_line"
    ::= { assetsZooGraphingXYGraphsGraphingBlocksBlueprintPlotOaDataRu9b2c 46406 }

assetsZooGraphingXYGraphsGraphingBlocksBlueprintPlotSettings475e OBJECT IDENTIFIER ::= { assetsZooGraphingXYGraphsGraphingBlocksBlueprintPlotdc99 21716 }
-- MQTT: OPEN-AIR/Assets/Zoo/graphing/XY_Graphs/Graphing/blocks/Blueprint_Plot/settings/x_label
assetsZooGraphingXYGraphsGraphingBlocksBlueprintPlotSettings2634 OBJECT-TYPE
    SYNTAX      DisplayString
    MAX-ACCESS  read-write
    STATUS      current
    DESCRIPTION "Source: OPEN-AIR/Assets/Zoo/graphing/XY_Graphs/Graphing/blocks/Blueprint_Plot/settings/x_label"
    ::= { assetsZooGraphingXYGraphsGraphingBlocksBlueprintPlotSettings475e 29844 }

assetsZooGraphingXYGraphsGraphingZoodatagraphingXYGraphsGrap8476 OBJECT IDENTIFIER ::= { assetsZooGraphingXYGraphsGraphingf0fa 62163 }
assetsZooGraphingXYGraphsGraphingZoodatagraphingXYGraphsGrapd6e3 OBJECT IDENTIFIER ::= { assetsZooGraphingXYGraphsGraphingZoodatagraphingXYGraphsGrap8476 14105 }
assetsZooGraphingXYGraphsGraphingZoodatagraphingXYGraphsGrap890b OBJECT IDENTIFIER ::= { assetsZooGraphingXYGraphsGraphingZoodatagraphingXYGraphsGrapd6e3 1143 }
assetsZooGraphingXYGraphsGraphingZoodatagraphingXYGraphsGrapbce3 OBJECT IDENTIFIER ::= { assetsZooGraphingXYGraphsGraphingZoodatagraphingXYGraphsGrap890b 14500 }
-- MQTT: OPEN-AIR/Assets/Zoo/graphing/XY_Graphs/Graphing/Zoo_data_graphing_XY_Graphs_Graphing_2/blocks/Cubic_Plot/oaDataRunningFiles/x_cubed
assetsZooGraphingXYGraphsGraphingZoodatagraphingXYGraphsGrapc327 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Cubic_Plot/oaDataRunningFiles/x_cubed"
    ::= { assetsZooGraphingXYGraphsGraphingZoodatagraphingXYGraphsGrapbce3 32089 }

assetsZooGraphingXYGraphsGraphingZoodatagraphingXYGraphsGrap1016 OBJECT IDENTIFIER ::= { assetsZooGraphingXYGraphsGraphingZoodatagraphingXYGraphsGrap890b 38780 }
-- MQTT: OPEN-AIR/Assets/Zoo/graphing/XY_Graphs/Graphing/Zoo_data_graphing_XY_Graphs_Graphing_2/blocks/Cubic_Plot/settings/ylim
assetsZooGraphingXYGraphsGraphingZoodatagraphingXYGraphsGrap1ba9 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Cubic_Plot/settings/ylim"
    ::= { assetsZooGraphingXYGraphsGraphingZoodatagraphingXYGraphsGrap1016 18129 }

-- MQTT: OPEN-AIR/Assets/Zoo/graphing/XY_Graphs/Graphing/Zoo_data_graphing_XY_Graphs_Graphing_2/blocks/Cubic_Plot/settings/x_label
assetsZooGraphingXYGraphsGraphingZoodatagraphingXYGraphsGrapcb51 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Cubic_Plot/settings/x_label"
    ::= { assetsZooGraphingXYGraphsGraphingZoodatagraphingXYGraphsGrap1016 38497 }

-- MQTT: OPEN-AIR/Assets/Zoo/graphing/XY_Graphs/Graphing/Zoo_data_graphing_XY_Graphs_Graphing_2/blocks/Cubic_Plot/settings/show_grid
assetsZooGraphingXYGraphsGraphingZoodatagraphingXYGraphsGrapd689 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Cubic_Plot/settings/show_grid"
    ::= { assetsZooGraphingXYGraphsGraphingZoodatagraphingXYGraphsGrap1016 50674 }

assetsZooGraphingXYGraphsGraphingZoodatagraphingXYGraphsGrap3a22 OBJECT IDENTIFIER ::= { assetsZooGraphingXYGraphsGraphingZoodatagraphingXYGraphsGrapd6e3 13484 }
assetsZooGraphingXYGraphsGraphingZoodatagraphingXYGraphsGrap6a92 OBJECT IDENTIFIER ::= { assetsZooGraphingXYGraphsGraphingZoodatagraphingXYGraphsGrap3a22 57872 }
-- MQTT: OPEN-AIR/Assets/Zoo/graphing/XY_Graphs/Graphing/Zoo_data_graphing_XY_Graphs_Graphing_2/blocks/Quadratic_Plot/oaDataRunningFiles/x_squared
assetsZooGraphingXYGraphsGraphingZoodatagraphingXYGraphsGrap41da OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Quadratic_Plot/oaDataRunningFiles/x_squared"
    ::= { assetsZooGraphingXYGraphsGraphingZoodatagraphingXYGraphsGrap6a92 21944 }

assetsZooGraphingXYGraphsGraphingZoodatagraphingXYGraphsGrap8c34 OBJECT IDENTIFIER ::= { assetsZooGraphingXYGraphsGraphingZoodatagraphingXYGraphsGrapd6e3 17837 }
assetsZooGraphingXYGraphsGraphingZoodatagraphingXYGraphsGrapa33d OBJECT IDENTIFIER ::= { assetsZooGraphingXYGraphsGraphingZoodatagraphingXYGraphsGrap8c34 30660 }
-- MQTT: OPEN-AIR/Assets/Zoo/graphing/XY_Graphs/Graphing/Zoo_data_graphing_XY_Graphs_Graphing_2/blocks/Damped_Sine_Wave/oaDataRunningFiles/damped_sine
assetsZooGraphingXYGraphsGraphingZoodatagraphingXYGraphsGrap239b OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Damped_Sine_Wave/oaDataRunningFiles/damped_sine"
    ::= { assetsZooGraphingXYGraphsGraphingZoodatagraphingXYGraphsGrapa33d 46840 }

assetsZooGraphingXYGraphsGraphingZoodatagraphingXYGraphsGrap4162 OBJECT IDENTIFIER ::= { assetsZooGraphingXYGraphsGraphingZoodatagraphingXYGraphsGrapd6e3 21567 }
assetsZooGraphingXYGraphsGraphingZoodatagraphingXYGraphsGrap7fa7 OBJECT IDENTIFIER ::= { assetsZooGraphingXYGraphsGraphingZoodatagraphingXYGraphsGrap4162 45795 }
-- MQTT: OPEN-AIR/Assets/Zoo/graphing/XY_Graphs/Graphing/Zoo_data_graphing_XY_Graphs_Graphing_2/blocks/Another_Log_Plot/oaDataRunningFiles/log_data_2
assetsZooGraphingXYGraphsGraphingZoodatagraphingXYGraphsGrap97bb OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Another_Log_Plot/oaDataRunningFiles/log_data_2"
    ::= { assetsZooGraphingXYGraphsGraphingZoodatagraphingXYGraphsGrap7fa7 14151 }

assetsZooGraphingXYGraphsGraphingZoodatagraphingXYGraphsGrap3898 OBJECT IDENTIFIER ::= { assetsZooGraphingXYGraphsGraphingZoodatagraphingXYGraphsGrapd6e3 30032 }
assetsZooGraphingXYGraphsGraphingZoodatagraphingXYGraphsGrap99ca OBJECT IDENTIFIER ::= { assetsZooGraphingXYGraphsGraphingZoodatagraphingXYGraphsGrap3898 17769 }
-- MQTT: OPEN-AIR/Assets/Zoo/graphing/XY_Graphs/Graphing/Zoo_data_graphing_XY_Graphs_Graphing_2/blocks/Random_Walk/settings/show_grid
assetsZooGraphingXYGraphsGraphingZoodatagraphingXYGraphsGrap61c3 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Random_Walk/settings/show_grid"
    ::= { assetsZooGraphingXYGraphsGraphingZoodatagraphingXYGraphsGrap99ca 10899 }

-- MQTT: OPEN-AIR/Assets/Zoo/graphing/XY_Graphs/Graphing/Zoo_data_graphing_XY_Graphs_Graphing_2/blocks/Random_Walk/settings/xlim
assetsZooGraphingXYGraphsGraphingZoodatagraphingXYGraphsGrape99a OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Random_Walk/settings/xlim"
    ::= { assetsZooGraphingXYGraphsGraphingZoodatagraphingXYGraphsGrap99ca 42754 }

-- MQTT: OPEN-AIR/Assets/Zoo/graphing/XY_Graphs/Graphing/Zoo_data_graphing_XY_Graphs_Graphing_2/blocks/Random_Walk/settings/ylim
assetsZooGraphingXYGraphsGraphingZoodatagraphingXYGraphsGrap5126 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Random_Walk/settings/ylim"
    ::= { assetsZooGraphingXYGraphsGraphingZoodatagraphingXYGraphsGrap99ca 49255 }

assetsZooGraphingXYGraphsGraphingZoodatagraphingXYGraphsGrapba9d OBJECT IDENTIFIER ::= { assetsZooGraphingXYGraphsGraphingZoodatagraphingXYGraphsGrap3898 55237 }
-- MQTT: OPEN-AIR/Assets/Zoo/graphing/XY_Graphs/Graphing/Zoo_data_graphing_XY_Graphs_Graphing_2/blocks/Random_Walk/oaDataRunningFiles/random
assetsZooGraphingXYGraphsGraphingZoodatagraphingXYGraphsGrap3848 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Random_Walk/oaDataRunningFiles/random"
    ::= { assetsZooGraphingXYGraphsGraphingZoodatagraphingXYGraphsGrapba9d 2848 }

assetsZooGraphingXYGraphsGraphingZoodatagraphingXYGraphsGrap95d7 OBJECT IDENTIFIER ::= { assetsZooGraphingXYGraphsGraphingZoodatagraphingXYGraphsGrapd6e3 32753 }
assetsZooGraphingXYGraphsGraphingZoodatagraphingXYGraphsGrap3e4f OBJECT IDENTIFIER ::= { assetsZooGraphingXYGraphsGraphingZoodatagraphingXYGraphsGrap95d7 43700 }
-- MQTT: OPEN-AIR/Assets/Zoo/graphing/XY_Graphs/Graphing/Zoo_data_graphing_XY_Graphs_Graphing_2/blocks/Square_Root_Plot/oaDataRunningFiles/sqrt_x
assetsZooGraphingXYGraphsGraphingZoodatagraphingXYGraphsGrapba44 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Square_Root_Plot/oaDataRunningFiles/sqrt_x"
    ::= { assetsZooGraphingXYGraphsGraphingZoodatagraphingXYGraphsGrap3e4f 10532 }

-- MQTT: OPEN-AIR/Assets/Zoo/graphing/XY_Graphs/Graphing/Zoo_data_graphing_XY_Graphs_Graphing_2/blocks/Square_Root_Plot/oaDataRunningFiles/MARKERS
assetsZooGraphingXYGraphsGraphingZoodatagraphingXYGraphsGrapc8e9 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Square_Root_Plot/oaDataRunningFiles/MARKERS"
    ::= { assetsZooGraphingXYGraphsGraphingZoodatagraphingXYGraphsGrap3e4f 17918 }

assetsZooGraphingXYGraphsGraphingZoodatagraphingXYGraphsGrapaad6 OBJECT IDENTIFIER ::= { assetsZooGraphingXYGraphsGraphingZoodatagraphingXYGraphsGrap95d7 43818 }
-- MQTT: OPEN-AIR/Assets/Zoo/graphing/XY_Graphs/Graphing/Zoo_data_graphing_XY_Graphs_Graphing_2/blocks/Square_Root_Plot/settings/x_label
assetsZooGraphingXYGraphsGraphingZoodatagraphingXYGraphsGrap7c44 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Square_Root_Plot/settings/x_label"
    ::= { assetsZooGraphingXYGraphsGraphingZoodatagraphingXYGraphsGrapaad6 44295 }

assetsZooGraphingXYGraphsGraphingZoodatagraphingXYGraphsGrap2b8f OBJECT IDENTIFIER ::= { assetsZooGraphingXYGraphsGraphingZoodatagraphingXYGraphsGrapd6e3 36315 }
assetsZooGraphingXYGraphsGraphingZoodatagraphingXYGraphsGrap767f OBJECT IDENTIFIER ::= { assetsZooGraphingXYGraphsGraphingZoodatagraphingXYGraphsGrap2b8f 1649 }
-- MQTT: OPEN-AIR/Assets/Zoo/graphing/XY_Graphs/Graphing/Zoo_data_graphing_XY_Graphs_Graphing_2/blocks/Inverse_Plot/settings/title
assetsZooGraphingXYGraphsGraphingZoodatagraphingXYGraphsGrap8632 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Inverse_Plot/settings/title"
    ::= { assetsZooGraphingXYGraphsGraphingZoodatagraphingXYGraphsGrap767f 5850 }

-- MQTT: OPEN-AIR/Assets/Zoo/graphing/XY_Graphs/Graphing/Zoo_data_graphing_XY_Graphs_Graphing_2/blocks/Inverse_Plot/settings/show_grid
assetsZooGraphingXYGraphsGraphingZoodatagraphingXYGraphsGrapd95b OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Inverse_Plot/settings/show_grid"
    ::= { assetsZooGraphingXYGraphsGraphingZoodatagraphingXYGraphsGrap767f 55920 }

assetsZooGraphingXYGraphsGraphingZoodatagraphingXYGraphsGrapb331 OBJECT IDENTIFIER ::= { assetsZooGraphingXYGraphsGraphingZoodatagraphingXYGraphsGrap2b8f 10022 }
-- MQTT: OPEN-AIR/Assets/Zoo/graphing/XY_Graphs/Graphing/Zoo_data_graphing_XY_Graphs_Graphing_2/blocks/Inverse_Plot/oaDataRunningFiles/inverse_x
assetsZooGraphingXYGraphsGraphingZoodatagraphingXYGraphsGrap94ac OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Inverse_Plot/oaDataRunningFiles/inverse_x"
    ::= { assetsZooGraphingXYGraphsGraphingZoodatagraphingXYGraphsGrapb331 22789 }

assetsZooGraphingXYGraphsGraphingZoodatagraphingXYGraphsGrapf876 OBJECT IDENTIFIER ::= { assetsZooGraphingXYGraphsGraphingZoodatagraphingXYGraphsGrapd6e3 56503 }
assetsZooGraphingXYGraphsGraphingZoodatagraphingXYGraphsGrap41ea OBJECT IDENTIFIER ::= { assetsZooGraphingXYGraphsGraphingZoodatagraphingXYGraphsGrapf876 10176 }
-- MQTT: OPEN-AIR/Assets/Zoo/graphing/XY_Graphs/Graphing/Zoo_data_graphing_XY_Graphs_Graphing_2/blocks/Matrix_Scatter/oaDataRunningFiles/matrix_dots
assetsZooGraphingXYGraphsGraphingZoodatagraphingXYGraphsGrapd789 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Matrix_Scatter/oaDataRunningFiles/matrix_dots"
    ::= { assetsZooGraphingXYGraphsGraphingZoodatagraphingXYGraphsGrap41ea 21670 }

assetsZooGraphingXYGraphsGraphingZoodatagraphingXYGraphsGrap30e8 OBJECT IDENTIFIER ::= { assetsZooGraphingXYGraphsGraphingZoodatagraphingXYGraphsGrapf876 38418 }
-- MQTT: OPEN-AIR/Assets/Zoo/graphing/XY_Graphs/Graphing/Zoo_data_graphing_XY_Graphs_Graphing_2/blocks/Matrix_Scatter/settings/y_label
assetsZooGraphingXYGraphsGraphingZoodatagraphingXYGraphsGrape069 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Matrix_Scatter/settings/y_label"
    ::= { assetsZooGraphingXYGraphsGraphingZoodatagraphingXYGraphsGrap30e8 29573 }

-- MQTT: OPEN-AIR/Assets/Zoo/graphing/XY_Graphs/Graphing/Zoo_data_graphing_XY_Graphs_Graphing_2/blocks/Matrix_Scatter/settings/x_label
assetsZooGraphingXYGraphsGraphingZoodatagraphingXYGraphsGrap461e OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Matrix_Scatter/settings/x_label"
    ::= { assetsZooGraphingXYGraphsGraphingZoodatagraphingXYGraphsGrap30e8 30769 }

assetsZooGraphingXYGraphsGraphingZoodatagraphingXYGraphsGrap7ea5 OBJECT IDENTIFIER ::= { assetsZooGraphingXYGraphsGraphingZoodatagraphingXYGraphsGrapd6e3 57901 }
assetsZooGraphingXYGraphsGraphingZoodatagraphingXYGraphsGrap7309 OBJECT IDENTIFIER ::= { assetsZooGraphingXYGraphsGraphingZoodatagraphingXYGraphsGrap7ea5 49594 }
-- MQTT: OPEN-AIR/Assets/Zoo/graphing/XY_Graphs/Graphing/Zoo_data_graphing_XY_Graphs_Graphing_2/blocks/Step_Plot/oaDataRunningFiles/step_data
assetsZooGraphingXYGraphsGraphingZoodatagraphingXYGraphsGrapac17 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Step_Plot/oaDataRunningFiles/step_data"
    ::= { assetsZooGraphingXYGraphsGraphingZoodatagraphingXYGraphsGrap7309 38865 }

assetsZooGraphingXYGraphsGraphingZoodatagraphingXYGraphsGrapadd6 OBJECT IDENTIFIER ::= { assetsZooGraphingXYGraphsGraphingZoodatagraphingXYGraphsGrap7ea5 61920 }
-- MQTT: OPEN-AIR/Assets/Zoo/graphing/XY_Graphs/Graphing/Zoo_data_graphing_XY_Graphs_Graphing_2/blocks/Step_Plot/settings/xlim
assetsZooGraphingXYGraphsGraphingZoodatagraphingXYGraphsGrap696a OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Step_Plot/settings/xlim"
    ::= { assetsZooGraphingXYGraphsGraphingZoodatagraphingXYGraphsGrapadd6 1487 }

-- MQTT: OPEN-AIR/Assets/Zoo/graphing/XY_Graphs/Graphing/Zoo_data_graphing_XY_Graphs_Graphing_2/blocks/Step_Plot/settings/y_label
assetsZooGraphingXYGraphsGraphingZoodatagraphingXYGraphsGrap4d09 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Step_Plot/settings/y_label"
    ::= { assetsZooGraphingXYGraphsGraphingZoodatagraphingXYGraphsGrapadd6 38821 }

-- MQTT: OPEN-AIR/Assets/Zoo/graphing/XY_Graphs/Graphing/Zoo_data_graphing_XY_Graphs_Graphing_2/blocks/Step_Plot/settings/title
assetsZooGraphingXYGraphsGraphingZoodatagraphingXYGraphsGrap1ba3 OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Step_Plot/settings/title"
    ::= { assetsZooGraphingXYGraphsGraphingZoodatagraphingXYGraphsGrapadd6 54063 }

assetsZooGraphingXYGraphsGraphingZoodatagraphingXYGraphsGrap7729 OBJECT IDENTIFIER ::= { assetsZooGraphingXYGraphsGraphingZoodatagraphingXYGraphsGrapd6e3 60082 }
assetsZooGraphingXYGraphsGraphingZoodatagraphingXYGraphsGrap3a6b OBJECT IDENTIFIER ::= { assetsZooGraphingXYGraphsGraphingZoodatagraphingXYGraphsGrap7729 46836 }
-- MQTT: OPEN-AIR/Assets/Zoo/graphing/XY_Graphs/Graphing/Zoo_data_graphing_XY_Graphs_Graphing_2/blocks/Pulse_Train/settings/xlim
assetsZooGraphingXYGraphsGraphingZoodatagraphingXYGraphsGrap9ebc OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Pulse_Train/settings/xlim"
    ::= { assetsZooGraphingXYGraphsGraphingZoodatagraphingXYGraphsGrap3a6b 44350 }

assetsZooGraphingXYGraphsGraphingZoodatagraphingXYGraphsGrap5c7b OBJECT IDENTIFIER ::= { assetsZooGraphingXYGraphsGraphingZoodatagraphingXYGraphsGrap7729 46917 }
-- MQTT: OPEN-AIR/Assets/Zoo/graphing/XY_Graphs/Graphing/Zoo_data_graphing_XY_Graphs_Graphing_2/blocks/Pulse_Train/oaDataRunningFiles/pulses
assetsZooGraphingXYGraphsGraphingZoodatagraphingXYGraphsGrap766d OBJECT-TYPE
    SYNTAX      DisplayString
    MAX-ACCESS  read-write
    STATUS      current
    DESCRIPTION "Source: OPEN-AIR/Assets/Zoo/graphing/XY_Graphs/Graphing/Zoo_data_graphing_XY_Graphs_Graphing_2/blocks/Pulse_Train/oaDataRunningFiles/pulses"
    ::= { assetsZooGraphingXYGraphsGraphingZoodatagraphingXYGraphsGrap5c7b 52596 }

assetsZooGraphingXYGraphsDynamicgraphaefe OBJECT IDENTIFIER ::= { assetsZooGraphingXYGraphsa6ac 4 }
assetsZooGraphingXYGraphsDynamicgraphZoodatagraphingXYGraphs1b42 OBJECT IDENTIFIER ::= { assetsZooGraphingXYGraphsDynamicgraphaefe 7901 }
assetsZooGraphingXYGraphsDynamicgraphZoodatagraphingXYGraphs8d55 OBJECT IDENTIFIER ::= { assetsZooGraphingXYGraphsDynamicgraphZoodatagraphingXYGraphs1b42 30729 }
assetsZooGraphingXYGraphsDynamicgraphZoodatagraphingXYGraphs9afc OBJECT IDENTIFIER ::= { assetsZooGraphingXYGraphsDynamicgraphZoodatagraphingXYGraphs8d55 31872 }
assetsZooGraphingXYGraphsDynamicgraphZoodatagraphingXYGraphs37aa OBJECT IDENTIFIER ::= { assetsZooGraphingXYGraphsDynamicgraphZoodatagraphingXYGraphs9afc 45525 }
assetsZooGraphingXYGraphsDynamicgraphZoodatagraphingXYGraphs69b0 OBJECT IDENTIFIER ::= { assetsZooGraphingXYGraphsDynamicgraphZoodatagraphingXYGraphs37aa 42560 }
assetsZooGraphingXYGraphsDynamicgraphZoodatagraphingXYGraphs8618 OBJECT IDENTIFIER ::= { assetsZooGraphingXYGraphsDynamicgraphZoodatagraphingXYGraphs69b0 55886 }
-- MQTT: OPEN-AIR/Assets/Zoo/graphing/XY_Graphs/dynamic_graph/Zoo_data_graphing_XY_Graphs_dynamic_graph_2/blocks/elements/dynamic_graph_examples/step_graph/settings/title
assetsZooGraphingXYGraphsDynamicgraphZoodatagraphingXYGraphs2c2e OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph_2/blocks/elements/dynamic_graph_examples/step_graph/settings/title"
    ::= { assetsZooGraphingXYGraphsDynamicgraphZoodatagraphingXYGraphs8618 36240 }

assetsZooGraphingXYGraphsDynamicgraphZoodatagraphingXYGraphs66aa OBJECT IDENTIFIER ::= { assetsZooGraphingXYGraphsDynamicgraphZoodatagraphingXYGraphs69b0 57285 }
-- MQTT: OPEN-AIR/Assets/Zoo/graphing/XY_Graphs/dynamic_graph/Zoo_data_graphing_XY_Graphs_dynamic_graph_2/blocks/elements/dynamic_graph_examples/step_graph/oaDataRunningFiles/logic_signal
assetsZooGraphingXYGraphsDynamicgraphZoodatagraphingXYGraphs1909 OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph_2/blocks/elements/dynamic_graph_examples/step_graph/oaDataRunningFiles/logic_signal"
    ::= { assetsZooGraphingXYGraphsDynamicgraphZoodatagraphingXYGraphs66aa 33370 }

assetsZooGraphingXYGraphsDynamicgraphZoodatagraphingXYGraphsf627 OBJECT IDENTIFIER ::= { assetsZooGraphingXYGraphsDynamicgraphZoodatagraphingXYGraphs37aa 54759 }
assetsZooGraphingXYGraphsDynamicgraphZoodatagraphingXYGraphsa902 OBJECT IDENTIFIER ::= { assetsZooGraphingXYGraphsDynamicgraphZoodatagraphingXYGraphsf627 10606 }
-- MQTT: OPEN-AIR/Assets/Zoo/graphing/XY_Graphs/dynamic_graph/Zoo_data_graphing_XY_Graphs_dynamic_graph_2/blocks/elements/dynamic_graph_examples/log_demo_graph/oaDataRunningFiles/exp_growth
assetsZooGraphingXYGraphsDynamicgraphZoodatagraphingXYGraphs3d06 OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph_2/blocks/elements/dynamic_graph_examples/log_demo_graph/oaDataRunningFiles/exp_growth"
    ::= { assetsZooGraphingXYGraphsDynamicgraphZoodatagraphingXYGraphsa902 59213 }

-- MQTT: OPEN-AIR/Assets/Zoo/graphing/XY_Graphs/dynamic_graph/Zoo_data_graphing_XY_Graphs_dynamic_graph_2/blocks/elements/dynamic_graph_examples/log_demo_graph/oaDataRunningFiles/power_law
assetsZooGraphingXYGraphsDynamicgraphZoodatagraphingXYGraphs5cf8 OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph_2/blocks/elements/dynamic_graph_examples/log_demo_graph/oaDataRunningFiles/power_law"
    ::= { assetsZooGraphingXYGraphsDynamicgraphZoodatagraphingXYGraphsa902 64071 }

assetsZooGraphingXYGraphsDynamicgraphZoodatagraphingXYGraphsf557 OBJECT IDENTIFIER ::= { assetsZooGraphingXYGraphsDynamicgraphZoodatagraphingXYGraphs37aa 61281 }
assetsZooGraphingXYGraphsDynamicgraphZoodatagraphingXYGraphs89e3 OBJECT IDENTIFIER ::= { assetsZooGraphingXYGraphsDynamicgraphZoodatagraphingXYGraphsf557 56265 }
-- MQTT: OPEN-AIR/Assets/Zoo/graphing/XY_Graphs/dynamic_graph/Zoo_data_graphing_XY_Graphs_dynamic_graph_2/blocks/elements/dynamic_graph_examples/high_density_graph/settings/y_label
assetsZooGraphingXYGraphsDynamicgraphZoodatagraphingXYGraphse9d2 OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph_2/blocks/elements/dynamic_graph_examples/high_density_graph/settings/y_label"
    ::= { assetsZooGraphingXYGraphsDynamicgraphZoodatagraphingXYGraphs89e3 38864 }

assetsZooGraphingXYGraphsDynamicgraphZoodatagraphingXYGraphsb7ac OBJECT IDENTIFIER ::= { assetsZooGraphingXYGraphsDynamicgraphaefe 28504 }
assetsZooGraphingXYGraphsDynamicgraphZoodatagraphingXYGraphs75cb OBJECT IDENTIFIER ::= { assetsZooGraphingXYGraphsDynamicgraphZoodatagraphingXYGraphsb7ac 48187 }
assetsZooGraphingXYGraphsDynamicgraphZoodatagraphingXYGraphs4e64 OBJECT IDENTIFIER ::= { assetsZooGraphingXYGraphsDynamicgraphZoodatagraphingXYGraphs75cb 44916 }
assetsZooGraphingXYGraphsDynamicgraphZoodatagraphingXYGraphs8394 OBJECT IDENTIFIER ::= { assetsZooGraphingXYGraphsDynamicgraphZoodatagraphingXYGraphs4e64 4788 }
assetsZooGraphingXYGraphsDynamicgraphZoodatagraphingXYGraphsb88d OBJECT IDENTIFIER ::= { assetsZooGraphingXYGraphsDynamicgraphZoodatagraphingXYGraphs8394 4258 }
assetsZooGraphingXYGraphsDynamicgraphZoodatagraphingXYGraphs9297 OBJECT IDENTIFIER ::= { assetsZooGraphingXYGraphsDynamicgraphZoodatagraphingXYGraphsb88d 42779 }
-- MQTT: OPEN-AIR/Assets/Zoo/graphing/XY_Graphs/dynamic_graph/Zoo_data_graphing_XY_Graphs_dynamic_graph/blocks/elements/dynamic_graph_examples/simple_graph/settings/title
assetsZooGraphingXYGraphsDynamicgraphZoodatagraphingXYGraphsdf3a OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph/blocks/elements/dynamic_graph_examples/simple_graph/settings/title"
    ::= { assetsZooGraphingXYGraphsDynamicgraphZoodatagraphingXYGraphs9297 40299 }

assetsZooGraphingXYGraphsDynamicgraphZoodatagraphingXYGraphs1643 OBJECT IDENTIFIER ::= { assetsZooGraphingXYGraphsDynamicgraphZoodatagraphingXYGraphs8394 51036 }
assetsZooGraphingXYGraphsDynamicgraphZoodatagraphingXYGraphs7f4f OBJECT IDENTIFIER ::= { assetsZooGraphingXYGraphsDynamicgraphZoodatagraphingXYGraphs1643 21598 }
-- MQTT: OPEN-AIR/Assets/Zoo/graphing/XY_Graphs/dynamic_graph/Zoo_data_graphing_XY_Graphs_dynamic_graph/blocks/elements/dynamic_graph_examples/frequency_plot/settings/xlim
assetsZooGraphingXYGraphsDynamicgraphZoodatagraphingXYGraphsfde4 OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph/blocks/elements/dynamic_graph_examples/frequency_plot/settings/xlim"
    ::= { assetsZooGraphingXYGraphsDynamicgraphZoodatagraphingXYGraphs7f4f 32367 }

-- MQTT: OPEN-AIR/Assets/Zoo/graphing/XY_Graphs/dynamic_graph/Zoo_data_graphing_XY_Graphs_dynamic_graph/blocks/elements/dynamic_graph_examples/frequency_plot/settings/y_label
assetsZooGraphingXYGraphsDynamicgraphZoodatagraphingXYGraphs1b63 OBJECT-TYPE
    SYNTAX      DisplayString
    MAX-ACCESS  read-write
    STATUS      current
    DESCRIPTION "Source: OPEN-AIR/Assets/Zoo/graphing/XY_Graphs/dynamic_graph/Zoo_data_graphing_XY_Graphs_dynamic_graph/blocks/elements/dynamic_graph_examples/frequency_plot/settings/y_label"
    ::= { assetsZooGraphingXYGraphsDynamicgraphZoodatagraphingXYGraphs7f4f 50251 }

assetsZooGraphingXYGraphsBargrapha20c OBJECT IDENTIFIER ::= { assetsZooGraphingXYGraphsa6ac 5 }
assetsZooGraphingXYGraphsBargraphZoodatagraphingXYGraphsBarg476b OBJECT IDENTIFIER ::= { assetsZooGraphingXYGraphsBargrapha20c 46559 }
assetsZooGraphingXYGraphsBargraphZoodatagraphingXYGraphsBarg241b OBJECT IDENTIFIER ::= { assetsZooGraphingXYGraphsBargraphZoodatagraphingXYGraphsBarg476b 30050 }
assetsZooGraphingXYGraphsBargraphZoodatagraphingXYGraphsBargf5e8 OBJECT IDENTIFIER ::= { assetsZooGraphingXYGraphsBargraphZoodatagraphingXYGraphsBarg241b 14378 }
assetsZooGraphingXYGraphsBargraphZoodatagraphingXYGraphsBargcd42 OBJECT IDENTIFIER ::= { assetsZooGraphingXYGraphsBargraphZoodatagraphingXYGraphsBargf5e8 63108 }
assetsZooGraphingXYGraphsBargraphZoodatagraphingXYGraphsBargf641 OBJECT IDENTIFIER ::= { assetsZooGraphingXYGraphsBargraphZoodatagraphingXYGraphsBargcd42 6489 }
assetsZooGraphingXYGraphsBargraphZoodatagraphingXYGraphsBarg6919 OBJECT IDENTIFIER ::= { assetsZooGraphingXYGraphsBargraphZoodatagraphingXYGraphsBargf641 11038 }
-- MQTT: OPEN-AIR/Assets/Zoo/graphing/XY_Graphs/Bar_graph/Zoo_data_graphing_XY_Graphs_Bar_graph/blocks/elements/bar_graph_examples/simple_bar_graph/oaDataRunningFiles/ds_usage
assetsZooGraphingXYGraphsBargraphZoodatagraphingXYGraphsBargc4d2 OBJECT-TYPE
    SYNTAX      DisplayString
    MAX-ACCESS  read-write
    STATUS      current
    DESCRIPTION "Source: OPEN-AIR/Assets/Zoo/graphing/XY_Graphs/Bar_graph/Zoo_data_graphing_XY_Graphs_Bar_graph/blocks/elements/bar_graph_examples/simple_bar_graph/oaDataRunningFiles/ds_usage"
    ::= { assetsZooGraphingXYGraphsBargraphZoodatagraphingXYGraphsBarg6919 19976 }

-- MQTT: OPEN-AIR/Assets/Zoo/graphing/XY_Graphs/Bar_graph/Zoo_data_graphing_XY_Graphs_Bar_graph/blocks/elements/bar_graph_examples/simple_bar_graph/oaDataRunningFiles/MARKERS
assetsZooGraphingXYGraphsBargraphZoodatagraphingXYGraphsBarg8de1 OBJECT-TYPE
    SYNTAX      DisplayString
    MAX-ACCESS  read-write
    STATUS      current
    DESCRIPTION "Source: OPEN-AIR/Assets/Zoo/graphing/XY_Graphs/Bar_graph/Zoo_data_graphing_XY_Graphs_Bar_graph/blocks/elements/bar_graph_examples/simple_bar_graph/oaDataRunningFiles/MARKERS"
    ::= { assetsZooGraphingXYGraphsBargraphZoodatagraphingXYGraphsBarg6919 42957 }

assetsZooImagesebf2 OBJECT IDENTIFIER ::= { assetsZoo5f4e 4 }
assetsZooImagesProgressbarff57 OBJECT IDENTIFIER ::= { assetsZooImagesebf2 3 }
assetsZooImagesProgressbarZooimagesprogressbarb064 OBJECT IDENTIFIER ::= { assetsZooImagesProgressbarff57 4223 }
assetsZooImagesProgressbarZooimagesprogressbarBlocksb380 OBJECT IDENTIFIER ::= { assetsZooImagesProgressbarZooimagesprogressbarb064 40862 }
assetsZooImagesProgressbarZooimagesprogressbarBlocksElements4b71 OBJECT IDENTIFIER ::= { assetsZooImagesProgressbarZooimagesprogressbarBlocksb380 10242 }
-- MQTT: OPEN-AIR/Assets/Zoo/images/progress_bar/Zoo_images_progress_bar/blocks/elements3/examplefields
assetsZooImagesProgressbarZooimagesprogressbarBlocksElementsed49 OBJECT-TYPE
    SYNTAX      DisplayString
    MAX-ACCESS  read-write
    STATUS      current
    DESCRIPTION "Source: OPEN-AIR/Assets/Zoo/images/progress_bar/Zoo_images_progress_bar/blocks/elements3/examplefields"
    ::= { assetsZooImagesProgressbarZooimagesprogressbarBlocksElements4b71 46555 }

assetsZooImagesProgressbarZooimagesprogressbarBlocksElementsd515 OBJECT IDENTIFIER ::= { assetsZooImagesProgressbarZooimagesprogressbarBlocksb380 48545 }
-- MQTT: OPEN-AIR/Assets/Zoo/images/progress_bar/Zoo_images_progress_bar/blocks/elements4/examplefields
assetsZooImagesProgressbarZooimagesprogressbarBlocksElements7648 OBJECT-TYPE
    SYNTAX      DisplayString
    MAX-ACCESS  read-write
    STATUS      current
    DESCRIPTION "Source: OPEN-AIR/Assets/Zoo/images/progress_bar/Zoo_images_progress_bar/blocks/elements4/examplefields"
    ::= { assetsZooImagesProgressbarZooimagesprogressbarBlocksElementsd515 47809 }

assetsSetsd54f OBJECT IDENTIFIER ::= { assets79d1 10 }
assetsSetsApplicationConfige0df OBJECT IDENTIFIER ::= { assetsSetsd54f 5 }
assetsSetsApplicationConfigDebug7405 OBJECT IDENTIFIER ::= { assetsSetsApplicationConfige0df 43924 }
-- MQTT: OPEN-AIR/Assets/sets/Application_Config/Debug/debug_enabled
assetsSetsApplicationConfigDebugDebugenabled8b51 OBJECT-TYPE
    SYNTAX      DisplayString
    MAX-ACCESS  read-write
    STATUS      current
    DESCRIPTION "Source: OPEN-AIR/Assets/sets/Application_Config/Debug/debug_enabled"
    ::= { assetsSetsApplicationConfigDebug7405 52564 }

assetsSetsFilepathsfa08 OBJECT IDENTIFIER ::= { assetsSetsd54f 6 }
-- MQTT: OPEN-AIR/Assets/sets/Filepaths/DATA_SCANS_PATH
assetsSetsFilepathsDATASCANSPATHcfca OBJECT-TYPE
    SYNTAX      DisplayString
    MAX-ACCESS  read-write
    STATUS      current
    DESCRIPTION "Source: OPEN-AIR/Assets/sets/Filepaths/DATA_SCANS_PATH"
    ::= { assetsSetsFilepathsfa08 7908 }

-- MQTT: OPEN-AIR/Assets/sets/Filepaths/CONFIG_MARKER_PATH
assetsSetsFilepathsCONFIGMARKERPATHde96 OBJECT-TYPE
    SYNTAX      DisplayString
    MAX-ACCESS  read-write
    STATUS      current
    DESCRIPTION "Source: OPEN-AIR/Assets/sets/Filepaths/CONFIG_MARKER_PATH"
    ::= { assetsSetsFilepathsfa08 41593 }

assetsRighttopd258 OBJECT IDENTIFIER ::= { assets79d1 65245 }
assetsRighttopBlocksba04 OBJECT IDENTIFIER ::= { assetsRighttopd258 19748 }
assetsRighttopBlocksControlButtons30e5 OBJECT IDENTIFIER ::= { assetsRighttopBlocksba04 19809 }
-- MQTT: OPEN-AIR/Assets/right_top/blocks/Control_Buttons/Pause
assetsRighttopBlocksControlButtonsPausef081 OBJECT-TYPE
    SYNTAX      DisplayString
    MAX-ACCESS  read-write
    STATUS      current
    DESCRIPTION "Source: OPEN-AIR/Assets/right_top/blocks/Control_Buttons/Pause"
    ::= { assetsRighttopBlocksControlButtons30e5 26413 }

tESTd87f OBJECT IDENTIFIER ::= { v1 32268 }
tESTRUST1d99 OBJECT IDENTIFIER ::= { tESTd87f 18592 }
-- MQTT: TEST/RUST/TOPIC
tESTRUSTTOPICb973 OBJECT-TYPE
    SYNTAX      DisplayString
    MAX-ACCESS  read-write
    STATUS      current
    DESCRIPTION "Source: TEST/RUST/TOPIC"
    ::= { tESTRUST1d99 41773 }

st213893c4 OBJECT IDENTIFIER ::= { v1 64224 }
st2138Device18bd OBJECT IDENTIFIER ::= { st213893c4 7455 }
st2138Device509090301d41 OBJECT IDENTIFIER ::= { st2138Device18bd 20383 }
st2138Device50909030Param2425 OBJECT IDENTIFIER ::= { st2138Device509090301d41 63905 }
st2138Device50909030ParamElements1db3c OBJECT IDENTIFIER ::= { st2138Device50909030Param2425 51695 }
-- MQTT: st2138/device/50909030/param/elements1/examplefields
st2138Device50909030ParamElements1Examplefields51c9 OBJECT-TYPE
    SYNTAX      DisplayString
    MAX-ACCESS  read-write
    STATUS      current
    DESCRIPTION "Source: st2138/device/50909030/param/elements1/examplefields"
    ::= { st2138Device50909030ParamElements1db3c 50381 }

st2138Device1ac47 OBJECT IDENTIFIER ::= { st2138Device18bd 20562 }
st2138Device1Param8a14 OBJECT IDENTIFIER ::= { st2138Device1ac47 16227 }
-- MQTT: st2138/device/1/param/frequency
st2138Device1ParamFrequency8265 OBJECT-TYPE
    SYNTAX      DisplayString
    MAX-ACCESS  read-write
    STATUS      current
    DESCRIPTION "Source: st2138/device/1/param/frequency"
    ::= { st2138Device1Param8a14 42635 }

-- MQTT: st2138/device/1/param/frequency_start
st2138Device1ParamFrequencystart7018 OBJECT-TYPE
    SYNTAX      DisplayString
    MAX-ACCESS  read-write
    STATUS      current
    DESCRIPTION "Source: st2138/device/1/param/frequency_start"
    ::= { st2138Device1Param8a14 65505 }

st2138Device1Cmd64e8 OBJECT IDENTIFIER ::= { st2138Device1ac47 31294 }
st2138Device1CmdPathsgroup30a3 OBJECT IDENTIFIER ::= { st2138Device1Cmd64e8 10112 }
-- MQTT: st2138/device/1/cmd/paths_group/path_fleet
st2138Device1CmdPathsgroupPathfleet4ad1 OBJECT-TYPE
    SYNTAX      DisplayString
    MAX-ACCESS  read-write
    STATUS      current
    DESCRIPTION "Source: st2138/device/1/cmd/paths_group/path_fleet"
    ::= { st2138Device1CmdPathsgroup30a3 54384 }

st2138Device1CmdHeadergroup68d3 OBJECT IDENTIFIER ::= { st2138Device1Cmd64e8 20461 }
-- MQTT: st2138/device/1/cmd/header_group/broker_port
st2138Device1CmdHeadergroupBrokerport62ca OBJECT-TYPE
    SYNTAX      DisplayString
    MAX-ACCESS  read-write
    STATUS      current
    DESCRIPTION "Source: st2138/device/1/cmd/header_group/broker_port"
    ::= { st2138Device1CmdHeadergroup68d3 59321 }

st2138Device509090425d365 OBJECT IDENTIFIER ::= { st2138Device18bd 36915 }
st2138Device509090425Paramf53f OBJECT IDENTIFIER ::= { st2138Device509090425d365 17311 }
st2138Device509090425Param5pointOneef9d OBJECT IDENTIFIER ::= { st2138Device509090425Paramf53f 64391 }
-- MQTT: st2138/device/509090425/param/5 point One/composite_drums
st2138Device509090425Param5pointOneCompositedrumsb937 OBJECT-TYPE
    SYNTAX      DisplayString
    MAX-ACCESS  read-write
    STATUS      current
    DESCRIPTION "Source: st2138/device/509090425/param/5 point One/composite_drums"
    ::= { st2138Device509090425Param5pointOneef9d 25503 }

END
