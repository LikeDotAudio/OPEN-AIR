OPENAIR-MIB DEFINITIONS ::= BEGIN

IMPORTS
    MODULE-IDENTITY, OBJECT-TYPE, enterprises FROM SNMPv2-SMI
    DisplayString FROM SNMPv2-TC;

openAirMIB MODULE-IDENTITY
    LAST-UPDATED "202603182252Z"
    ORGANIZATION "OPEN-AIR Project"
    CONTACT-INFO "Anthony Peter Kuzub"
    DESCRIPTION "MQTT-Aligned OID Tree for OPEN-AIR."
    REVISION "202603182252Z"
    DESCRIPTION "Strictly unique path-aligned generation."
    ::= { enterprises 25030 }

v1 OBJECT IDENTIFIER ::= { openAirMIB 1 }

unknownInstrument319b OBJECT IDENTIFIER ::= { v1 7871 }
yAKb471 OBJECT IDENTIFIER ::= { unknownInstrument319b 21184 }
unknown9eeb OBJECT IDENTIFIER ::= { yAKb471 6195 }
connectionb306 OBJECT IDENTIFIER ::= { unknown9eeb 33817 }
tablef5ff OBJECT IDENTIFIER ::= { connectionb306 13455 }
-- MQTT: OPEN-AIR/Unknown Instrument/YAK/Unknown/Connection/Table/type
typeb385 OBJECT-TYPE
    SYNTAX      DisplayString
    MAX-ACCESS  read-write
    STATUS      current
    DESCRIPTION "Source: OPEN-AIR/Unknown Instrument/YAK/Unknown/Connection/Table/type"
    ::= { tablef5ff 44637 }

-- MQTT: OPEN-AIR/Unknown Instrument/YAK/Unknown/Connection/Table/description
descriptiona0d5 OBJECT-TYPE
    SYNTAX      DisplayString
    MAX-ACCESS  read-write
    STATUS      current
    DESCRIPTION "Source: OPEN-AIR/Unknown Instrument/YAK/Unknown/Connection/Table/description"
    ::= { tablef5ff 60130 }

-- MQTT: OPEN-AIR/status
status7b00 OBJECT-TYPE
    SYNTAX      DisplayString
    MAX-ACCESS  read-write
    STATUS      current
    DESCRIPTION "Source: OPEN-AIR/status"
    ::= { v1 25884 }

dMM53cf OBJECT IDENTIFIER ::= { v1 45793 }
yAK32aa OBJECT IDENTIFIER ::= { dMM53cf 5745 }
a2a39 OBJECT IDENTIFIER ::= { yAK32aa 44112 }
connection9560 OBJECT IDENTIFIER ::= { a2a39 61057 }
tablef5c5 OBJECT IDENTIFIER ::= { connection9560 24000 }
-- MQTT: OPEN-AIR/DMM/YAK/34401A/Connection/Table/description
descriptionb66a OBJECT-TYPE
    SYNTAX      DisplayString
    MAX-ACCESS  read-write
    STATUS      current
    DESCRIPTION "Source: OPEN-AIR/DMM/YAK/34401A/Connection/Table/description"
    ::= { tablef5c5 30767 }

-- MQTT: OPEN-AIR/DMM/YAK/34401A/Connection/Table/type
type6f4b OBJECT-TYPE
    SYNTAX      DisplayString
    MAX-ACCESS  read-write
    STATUS      current
    DESCRIPTION "Source: OPEN-AIR/DMM/YAK/34401A/Connection/Table/type"
    ::= { tablef5c5 47370 }

END
